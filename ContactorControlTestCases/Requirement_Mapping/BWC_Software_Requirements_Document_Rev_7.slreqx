# BWC_Software_Requirements_Document_Rev_7

## BWC - Software Requirements Document - Rev 7: References to BWC - Software Requirements Document - Rev 7.docx (Container)
Read-only references to Microsoft Word document.
- srcFileChecksum: A31B9F6BF39219EB3CA26A6645B1195B

### Table of Contents (Functional)
Table of Contents
A General Requirements.. 0
A-1 Purpose. 0
A-2 Definitions. 0
A-3 Application. 0
A-4 Standards and Other Specifications. 0
A-5 California, Air Resource Board Regulation Implementation. 0
A-6 CARB and SAE J1979 Implementation for Model Year 2026. 1
A-7 CARB and SAE J1979-2 Implementation for Model Year 2027 and after 1
A-8 CARB and the Advanced Clean Car II (ACC II) Implementation. 1
B Regulatory Compliance.. 3
B-1 Responsibility for Compliance. 3
C Component Purpose.. 4
D Document Control. 5
D-1 Document Security. 5
D-2 Document Format 5
D-3 Change Authority. 5
D-4 Applicable Documents. 5
D-5 Order of Precedence. 5
E Independent Monitoring of the BPCM.. 6
E-1 Functional Safety. 6
F CAN Communications.. 7
F-1 CAN Requirements. 7
F-2 Internal controller signal data capture. 7
G DIDs.. 8
G-1 Descriptions of Part Number and ECU Identification DIDs. 8
H BPCM Power Up/Down and Initialization.. 9
H-1 BPCM Power Up and Initialization. 9
H-2 BPCM Shutdown/Power-Down Requirements. 10
I High Voltage Interlock Loop (HVIL) 12
I-1 HVIL Requirements. 12
I-2 High Voltage Interlock Status. 13
I-3 Diagnostics Associated with HVIL. 14
I-4 Calibrations Associated with HVIL. 15
I-5 CAN Signals Associated with HVIL. 15
J Contactor Control. 16
J-1 Contactor Control 16
J-2 Precharge. 21
J-3 Contactor Weld Check Diagnostics. 25
K Loss of Isolation Detection.. 27
K-1 General Requirements for Loss of Isolation (LOI) 27
K-2 Isolation Abort and Inhibit Requirement 27
K-3 Isolation Status. 27
K-4 Isolation Diagnostics. 28
K-5 Calibrations Associated with Isolation Detection. 28
K-6 CAN Signals Associated with Isolation Detection. 28
L Impact response by the BPCM.. 29
L-1 General Impact Response Requirements for BPCM.. 29
L-2 Impact Response Development 29
L-3 Optimal Thread. 30
L-4 Direct Delayed Thread. 30
L-5 Loss of Message Thread. 30
L-6 Impact Diagnostics. 31
L-7 Calibrations Associated with Isolation Detection. 31
L-8 CAN Signals Associated with Isolation Detection. 31
M Battery Conditioning (HVBatRdy) 32
M-1 Calibrations Associated with HVBatRdy. 33
M-2 Battery Pack Conditioning CAN Signals. 33
N Sensor Measurements.. 34
N-1 Current Measurement 34
N-2 Voltage Measurement 34
N-3 Temperature Measurement 36
N-4 Cell Voltage and Temperature Thresholds. 36
N-5 Cell Voltage and Temperature Sensor Diagnostics. 38
N-6 CAN Signals Associated with Sensor Measurements. 39
O Plug-In Charging.. 41
O-1 Plug-In Charging Algorithms. 41
O-2 Plug-In Charger Control 41
O-3 CAN Messages and Signals Associated with AC and DC Fast Plug-In Charging. 41
O-4 AC Plug-In Charging Procedure. 42
O-5 DC Fast Charge Plug-In Charging Procedure BEV.. 44
P (Optional) Cell Balancing.. 46
P-1 General Cell Balancing Requirements. 46
P-2 Cell Balancing Diagnostics and Protection. 46
P-3 Cell Balance Mode. 46
Q Thermal Management System Controls.. 47
Q-1 Heater Command. 48
Q-2 Thermal Runaway Requirements. 49
R State of Charge (SOC) Requirements.. 51
R-1 SOC Algorithm.. 51
R-2 Changing SOC Value. 51
R-3 SOC Definitions. 51
R-4 CAN Signals Associated with SOC.. 53
S State of Power (SOP) Requirements.. 54
S-1 Power Limit Estimation Algorithm.. 54
S-2 Static Power Limiting Tables. 54
S-3 Power Limits for Charge and Discharge. 54
S-4 Continuous Power Limit 55
S-5 Accuracy of Power Limit Estimation. 57
S-6 CAN Signals Associated with Power Limiting. 58
T (Optional) State of Health (SOH) Requirements. 59
T-1 SOH ¨C Capacity. 59
T-2 SOH ¨C Resistance (2 Signals) 60
T-3 Amp-Hour Throughput 60
T-4 Battery Data Recorder / Battery Usage History (BUH) 61
T-5 CAN Signals Associated with SOH.. 61
U Diagnostics Requirements.. 62
U-1 Diagnostic Robustness. 62
U-2 BPCM Warning and [Shutdown SW] Contactor Open Requirements. 63
U-3 Service Routine for Battery Pack Outside Normal Voltage Range. 63
U-4 Validation of DTCs. 63
U-5 Diagnostic Retry Strategy. 64
V Appendix A.. 65
V-1 Sensors. 65
V-2 CAN Signals. 65
W Abbreviations.. 66
X - Change Log.. 53

### General Requirements (Functional)

#### Purpose (Functional)
Purpose
This document defines the Core Software Requirements Document for the battery management system for Competition Organizer¡¯s BEV application. The purpose of this document is to describe the software that will be required by the Team. The scope of this document includes algorithms and processes that all teams are obligated to fulfill as well as algorithms and processes that are solely related to the battery pack assembly and its control module. All specifications are assumed to be understood unless specific and detailed questions are asked. This core software requirements document provides the best attempt to define up front to the Team the requirements for the BPCM (Battery Pack Control Module) software.

#### Definitions (Functional)
Definitions
The word “shall” is used to state binding requirements of the component defined by this document. These requirements shall be verifiable. The word “must” states requirements of other components and/or subsystems whose definitions are outside the scope this document. The word “will” is used to state conditions that result from immutable physical laws or conditions that result from adherence to other stated, binding requirements. The words “are” and will state definitions and facts that do not require verification. The word “withstand” will be defined as “Maintains design-intended functional and structural integrity while being subjected to the specified conditions.” The flowcharts used in this document are meant to facilitate the meaning and logic of the written requirements. The flowcharts themselves should not be construed as the requirements.

#### Application (Functional)
Application
Battery system related requirements, such as performance, interfaces, and hardware, are contained in Battery System Specifications and their referenced documents. Stellantis uses the terminology BPCM to designate the ECU used in this application. It is the responsibility of the Team to conform to these requirements and terminology in all documentation. This includes all presentations, diagrams, and conversations shared with Competition Organizers. The software shall be contained in the BPCM (Battery Pack Control Module), which is part of the battery pack system.

#### Standards and Other Specifications (Functional)
Standards and Other Specifications
In addition to the defined Battery System Specifications, Competition Organizers Specifications and Industry Standards shall be considered part of the BPCM requirements. The BPCM requirements contain BPCM Architecture, as well as corresponding requirements for PowerNet (Vehicle Architecture) applications for all regions.
The Team shall verify compliance to Industry Standards as provided in the Auxiliary (Excel) Specifications Table; which will be part of BMS core software requirements document included in the Source Package.
Each Specification in the Auxiliary (Excel) Specification Table shall be an item in the Software Compliance Matrix Sheet (All features Mapped out), as defined by the core software requirement BMS Support Document. Each specification will be considered a software compliance line item.

#### California, Air Resource Board R: California, Air Resource Board Regulation Implementation (Functional)
California, Air Resource Board Regulation Implementation
Not Applicable for Student Competition. For reference only:
The California Air Resource Board Regulations represent a Market and a time of sale. In this sense the BMS supported by this software requirements document shall require the ability to transition through the series of SAE J1979, SAE J1979-2, and SAE J1979-3, documents.

#### CARB and SAE J1979 Implementatio: CARB and SAE J1979 Implementation for Model Year 2026 (Functional)
CARB and SAE J1979 Implementation for Model Year 2026
Not Applicable for Student Competition. For reference only:
For Model Year 2026, the BMS shall communicate with the vehicle¡¯s OBD and test equipment based on SAE J1979 communication protocols. The communication is defined by an Open Systems Interconnection model, SAE J1979 and ISO 15031-5.
Through the implementation of SAE J1979 and ISO 15031-5, which include additional specifications for the successful implementation of CARB requirements for Model Year 2026, the BMS shall meet the requirements set by CARB standards, allowing the vehicle in which this battery management system is installed to be sold in the CARB regulation state of California and section 177 states who choose to adopt CARB rules for this time and marketplace.

#### CARB and SAE J1979-2 Implementat: CARB and SAE J1979-2 Implementation for Model Year 2027 and after (Functional)
CARB and SAE J1979-2 Implementation for Model Year 2027 and after
Not Applicable for Student Competition. For reference only:
For Model Year 2027 and after, the BMS shall communicate with the vehicle¡¯s OBD and test equipment based on SAE J1979-2 communication protocols. This specification defines the communication protocol and Open System Interconnect model layers which will allow the incorporation of OBD on UDS and the successful conformity to CARB requirements.
Through the implementation of SAE J1979-2 and ISO 14229-1, which include additional specifications for the successful implementation of CARB requirements for Model Year 2027 and beyond, the BMS shall meet the requirements set by CARB standards, allowing the vehicle in which this battery management system is installed to be sold in the CARB regulation state of California and section 177 states who choose to adopt CARB rules for this time and marketplace.

#### CARB and the Advanced Clean Car: CARB and the Advanced Clean Car II (ACC II) Implementation (Functional)
CARB and the Advanced Clean Car II (ACC II) Implementation
Not Applicable for Student Competition. For reference only:
For Model Year 2026 and after, the Team shall support the implementation of ACC II requirements. ACC II compliance is required to enable the PHEV and BMS system to obtain Zero Emission Vehicle Credits (ZEV) as identified in ZEV/Emissions Requirements.
The requirements defined here and additions to the requirements, including development needed to implement these changes throughout the program shall be covered by ED&D.
The ACC II requirements shall pertain to the following software criteria and systems to support the procurement of ACC II credits. Supporting regulations to be found in SAE J1979-3.
The Team shall implement the Standardized Data requirements for ZEV credit vehicles, associated with the reporting of BMS parameters on the instrument cluster, DIC, etc.
The Team shall support and provide software (if required) for PHEV High Powered US06 Cold Start Requirements. This may require software improvements to support hardware.
The Team shall support and provide software (if required) for PHEV battery SOH in-use reporting and CARB in-use confirmatory for SOH accuracy and range retention.
The BMS shall meet the requirements set by CARB ACC II standards, allowing the vehicle in which this battery management system is installed to obtain ACC II ZEV credits in the state of California and section 177 states who choose to adopt CARB rules for this time and marketplace.

### Regulatory Compliance (Functional)

#### Responsibility for Compliance (Functional)
Responsibility for Compliance
Not Applicable for Student Competition. For reference only:
It is responsibility of the Team to understand conformity measures and to recommend any changes to the specifications that are needed to meet regulations. Should it be determined for governmental compliance that post launch software is need; the Team will provide software changes in fully validated format within the normal time allotted.
After program launch, all software algorithms shall comply with all federal and state mandating rules.
In the event it is determined that the battery is not compliant with governmental regulations, the Team shall make all efforts to resolve this issue per interpretation of the regulations.

### Component Purpose (Functional)
Component Purpose
This document outlines the requirements for the BPCM. The BPCM monitors and reports battery pack cell voltages, battery pack and cell temperatures, cooling inlet and outlet temperatures, and battery pack current. The BPCM also calculates and reports power limits, state of charge, state of health, current and voltage limits. The functions, performance, reliability, and validation required for this component are outlined in this document. The basic function of the BPCM is the management of the battery pack cells and modules. The BPCM usually consists of a central electronic board and local cell supervising electronics for single cell supervision. BPCM functionality includes (but is not limited to) the measurement of battery current and battery voltage values during charge and discharge of battery and also protection from damage, such as overcharge, over discharge, and over/under temperature. It also provides HVIL monitoring and isolation measurement.

### Document Control (Functional)
Document Control
The information contained in this specification is considered to be Stellantis Confidential. ¡®Stellantis Confidential¡¯ is a designation for information, which has competitive value that, if disclosed, would have adverse consequences to Stellantis. As such, Stellantis intends to protect this information from disclosure to third parties (i.e. persons outside of Stellantis without a ¡®need to know¡¯).

#### Document Security (Functional)
Document Security
The Stellantis Information Security Practices and Procedures relating to the handling of Stellantis Confidential materials shall be followed.

#### Document Format (Functional)
Document Format
Sections, paragraphs, and sub-paragraphs of this specification will be uniquely numbered as a subset of the category and sub-category of the section into which they fall. Each lower-level requirement will bear the same number as its higher-level requirement and will be uniquely identified by the addition of necessary decimal places in the numbering scheme.

#### Change Authority (Functional)
Change Authority
Competition Organizers shall approve all changes to the format and/or content of this specification.
The final decision for any deviations from these requirements shall come from the Competition Organizers.

#### Applicable Documents (Functional)
Applicable Documents
This document directly expands upon, and flows down from, the requirements specified in the battery pack performance specification. Other documents referenced form a part of this specification to the extent specified herein. Unless otherwise noted, this specification refers to the most recent version of a particular document.

#### Order of Precedence (Functional)
Order of Precedence
In the event of a conflict between the text of this BMS core software requirement specification and any other Competition Organizers specification, the order of precedence are the other specifications, unless they are explicit to the battery pack software.
Those cases where a requirement fails to meet or exceed an applicable law or regulation or where a conflict occurs between requirements in documents referred to within this specification shall be reviewed by Competition Organizers and any changes to the specification shall be approved by Competition Organizers.

### Independent Monitoring of the BPCM (Functional)
Independent Monitoring of the BPCM
It will be suggested to have an independent method of assessing the integrity of the BPCM. When the integrity of the BPCM has been compromised, the appropriate action will be taken which may include the shutdown of the system.

#### Functional Safety (Functional)
Functional Safety
Not Required for Student Competition. For reference only:
The requirements for independent monitoring of the BPCM shall be determined by jointly conducting a functional safety analysis by the supplier. The final design configuration shall require Stellantis¡¯s approval.
Basic functional safety analysis can be proposed and reviewed with Stellantis.
Any discrepancies shall be brought forth to Stellantis for resolution.
Routines and DIDs which allow the verification of the functional safety requirements shall be available for vehicle testing.

### CAN Communications (Functional)

#### CAN Requirements (Functional)
CAN Requirements
The following is a non-comprehensive list of CAN requirements. For more information on CAN, see the Specifications Table.
The BPCM shall have at least 3 high-speed CAN channels (two for communication with other vehicle controllers, one for communicating sensor and operation values inside the battery pack). The BPCM CAN hardware will interface through a:
¡¤ Primary ePT
¡¤ Secondary ePT (redundant)
The messages on these CAN buses shall be sourced from the DBC and CMM files supplied by Stellantis. Before testing, ensure that all CAN signal mapping is verified. This is to ensure the correct value is being broadcast in the correct signal. Teams may use CANalyzer or a similar CAN tool to collect data at both the vehicle and battery pack levels.
All the attributes of vehicle CAN in the. dbc file should be validated for default values transitioning to actual values during initialization by the Team.
The following sections also outline several internal variables and calibratable parameters that Teams should consider implementing while developing their software controls. Teams should adapt all internal variables and calibratable parameters outlined to their own system since not all of them may be applicable, and some variables specific to your system may not be predefined.

#### Internal controller signal data capture (Functional)
Internal controller signal data capture
It is recommended for Teams to implement either an additional internal CAN bus (debugging bus) or something like ETAS xETK with INCA. This would be for data capture and debugging both in real time and afterwards.
If teams implement this, then this battery side connection should be available for when the battery pack is on the bench or in the vehicle while driving. The teams may choose to create a wiring breakout harness to interface between the vehicle harness and the battery pack.
Key data collected could be cell voltages, cell temperatures, coolant temperatures, feedback of individual contactor status, feedback from all current sensors, bus voltage, and any other internal variables that are needed for vehicle development.

### DIDs (Functional)
DIDs
Throughout this document, Teams will see references to ¡°adding DIDs¡± for various diagnostic situations. DIDs act to store information and can be especially useful for Teams as they build their controller.
Teams are expected to define their own DIDs and implement them as they see fit. Teams will have their Software Version Information DID read during various stages of testing in Y3.

#### Descriptions of Part Number and: Descriptions of Part Number and ECU Identification DIDs (Functional)
Descriptions of Part Number and ECU Identification DIDs
The following DIDs are an attachment of the Part Number and ECU Identification section of this document. The Software Version Information DIDs are required for Teams to implement. The Hardware Version Information is optional, but Teams are encouraged to implement it. Teams should have both hardware and software revision information and release notes to be available for review at any time by the OSC.
| ID | DID Name | DID Description |  |
| --- | --- | --- | --- |
| ID | DID Name | DID Description |  |
| RDI $F150 | ECU Hardware Version Information | Hardware version shall be used to revision and indicate any major hardware revisions to their controller and related hardware. |  |
| RDI $F151 | ECU Application Software MAJOR version | Teams shall follow semantic versioning for their BPCM Software Releases. $F151 shall indicate the MAJOR version of their software (example: 2.5.1) |  |
| RDI $F152 | ECU Application Software MINOR version | $F151 shall indicate the MINOR version of their software (example: 2.5.1) |  |
| RDI $F153 | ECU Application Software PATCH version | $F151 shall indicate the PATCH version of their software (example: 2.5.1) |  |

### BPCM Power Up/Down and Initialization (Functional)
BPCM Power Up/Down and Initialization
For both starting up and shutting down the system, there are two general sequences at play: power up/close contactors and open contactors/power down.
The general behavior of these sequences is expanded upon below. There are some exceptions in the order of events, which are outlined in the relevant section.

#### BPCM Power Up and Initialization (Functional)
BPCM Power Up and Initialization
This sequence powers on the BPCM and then closes the contactors. These are technically two separate sequences, so the conditions to close contactors do not exclusively require the BPCM to be on. The BPCM is responsible for controlling the actuation of the contactor when appropriate. In the case that the BPCM inhibits contactors from closing or determines a fault condition, it shall set the applicable diagnostic code.
Additionally, BPCM shall enable Loss of Communication diagnostics with EVCU independent of receiving the LOC Diagnostics Enable command from HCP (Hybrid Charge Controller, or the vehicle controller). The diagnostic shall be set after 5000 ms of wake-up.
Once the BPCM has received the proper wake-up signals to begin its initialization process, the BPCM shall first perform necessary functions to prepare for closing contactors. These functions include:
¡¤ Essential voltage, current, and temperature measurements specific to computing and reporting the available discharge power
¡¤ Sourcing of HVIL
¡¤ Reading EEPROM specific to last isolation state and SOC from previous ignition cycle
The events for Power Up/Initialization are listed below, and the BPCM shall not exceed the timings listed in the table:
|  |  | Closed via CAN |  |
| --- | --- | --- | --- |
| No. | Event | Event Timing (ms) | Total Timing (ms) |
| 1 | Wake-up signal received (12V input line for wake-up) | 0 | 0 |
| 2 | HVIL is sourced | 60 | 60 |
| 3 | Remaining BPCM initialization processes | 100 | 160 |
| 4 | All transmitted CAN signals are determined | 40 | 200 |
| 5 | BPCM transmits Contactor Status | 20 | 220 |
| 6 | Check that: Qualified Contactor Command = CLOSE and HVIL status = PASS Note: Timing assumes Contactor Command from Vehicle Controller is immediately received. This timing could be delayed if the BPCM waits for the HCP¡¯s Contactor Command (See Section I-1 Contactor Control). | 20 | 240 |
| 7 | Precharge sequence and negative contactor/precharge relay closed | 40 | 280 |
| 8 | BPCM transmits Battery Contactor Status as ¡°Precharging¡± | 20 | 300 |
| 9 | Precharge Process Time reaches 95% of pack voltage | 100 | 400 |
| 10 | BPCM Commands Positive Contactor Closed then commands Precharge sequence terminated | 40 | 440 |
| 11 | BPCM transmits Contactor Status as Closed | 30 | 470 |
The above is the standard sequence for powering up and closing contactors, however, keep in mind that sourcing HVIL is a separate process from closing contactors. It should, however, be done as soon as possible. To learn more about HVIL, move onto the next section of the SRD (H High Voltage Interlock Loop).

#### BPCM Shutdown/Power-Down Requirements (Functional)
BPCM Shutdown/Power-Down Requirements
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While implementing this and any other feature, teams must be sure not to accidentally set DTCs.
In order to properly determine if the Service Disconnect is out after the HCP Shutdown Command, the BPCM shall be permitted to continue sourcing its internal HVIL loop.
If the HVIL fails, then the isolation check shall be terminated so that a false isolation DTC is not set.

### High Voltage Interlock Loop (HVIL) (Functional)
High Voltage Interlock Loop (HVIL)
The High Voltage Interlock Loop (HVIL) shall provide an indication of the integrity of the High Voltage Propulsion Bus. When there is a break in the HVIL, it indicates that a high voltage component may be compromised or disconnected. The energy source and sink for the HVIL is the BPCM.
There shall be two ¡°HVIL type¡± loops in the battery pack. One HVIL loop is the external HVIL, which goes out through the High Voltage Propulsion Bus.
The other ¡°HVIL loop¡± is not a loop. It is a separate 12V power feed for the contactors, going through a Remote High Voltage Disconnect and Lockout (HVDL) and ending into the battery pack.

#### HVIL Requirements (Functional)

##### Sourcing External HVIL (Functional)
Sourcing External HVIL
To source external HVIL, the BPCM shall energize the HVIL circuit within Ke_t_HVILOnTimeout. This shall only be done when the following conditions are TRUE:
| Req # | Requirement |  |  | Additional Notes |
| --- | --- | --- | --- | --- |
| 1 | BPCM wake up from Sleep = TRUE (i.e. when the hardware wakeup line (ePT ECU Wakeup) is received) | OR | BPCM EPT Modes transitioning from OFF to ACCESSORY, RUN, or CRANK REQUEST | About 50ms (calibration value) delay may occur due to the initialization |
| 2 | On Initialization, startup inhibit flag is not set |  |  |  |
However, the Startup Inhibit Fault flag shall be set when ANY of the following conditions are true:
¡¤ BPCM Observed Impact Faults are TRUE on initialization
¡¤ BPCM Observed Loss of Internal Isolation Faults are TRUE on initialization
¡¤ BPCM Welded Contactor Faults are TRUE on initialization

##### De-Sourcing External HVIL (Functional)
De-Sourcing External HVIL
The BPCM shall de-energize the external HVIL circuit (stop the PWM) and set High Voltage Interlock Status to ¡°Not Sourced.¡± when ANY of the following are TRUE:
| Requirement |  |  |
| --- | --- | --- |
| The shutdown command is true (HCPShutDwnCmd = Shutdown) |  |  |
| Hardwired wakeup signal transitions from high to low | AND | HCP Loss of Comm = TRUE |
| Contactors are OPEN | AND | ePT wakeup transitions from High to Low |
| BPCM Observed Impact Faults are TRUE |  |  |

##### De-Sourcing Internal HVIL (Functional)
De-Sourcing Internal HVIL
There are two cases in which the BPCM should de-energize the internal HVIL circuit (stop the PWM).
The first case is when ALL the following are TRUE:
| Req # | Requirement |
| --- | --- |
| 1 | Contactors are Open (post weld check*) |
| 2 | Internal Isolation is Complete |
| 3 | BPCM is transitioning to Sleep Mode |
*The weld check is discussed more in I-3 and is a necessary requirement to ensure proper voltage discharge to a safe level.
The second case is when the BPCM observed Impact Faults are TRUE.

#### High Voltage Interlock Status (Functional)
High Voltage Interlock Status
The BPCM must report out the High Voltage Interlock Status signal (HVBatIntrlkStat). The requirements for each status are described below.
| HV Interlock Status | State Description | State Logic/Notes |
| --- | --- | --- |
| Undetermined (Not Sourced) | The BPCM has not sourced HVIL, cannot measure the HVIL circuit (i.e. prior to initial measurement or due to a BPCM hardware failure), or when HVIL circuit has been de-asserted after receiving HCPShutDwnCmd = Shutdown | ¡°Undetermined¡± may happen at the beginning of the BPCM wake up until the initial evaluation is complete or when HVIL circuit has been de-asserted after receiving the coordinated shutdown command |
| Pass | The BPCM senses the PWM frequency and duty cycle to be within range. | The test has run for a time equal to KeHVLR_t_HVILOpenSamplesDurationTime |
| Pass | The BPCM senses the PWM frequency and duty cycle to be within range. | The BPCM has not detected an electrical fault with the HVIL circuit (Shorted High, Shorted Low, Open for both External and Internal, OORL, OORH) |
| Fail | The BPCM senses the PWM frequency and duty cycle to be out of range. This is communicated to the vehicle system within 100ms via CAN HVBatIntrlkStat = Fail | The test has run for a time equal to KeHVLR_t_HVILOpenSamplesDurationTime |
| Fail | The BPCM senses the PWM frequency and duty cycle to be out of range. This is communicated to the vehicle system within 100ms via CAN HVBatIntrlkStat = Fail | The BPCM has detected an electrical fault with the HVIL circuit external or Internal to the battery (Open External, Open Internal, Out of Range Low (OORL), Out of Range High (OORH) |
| Invalid | The BPCM senses an invalid state of operation for the High Voltage Interlock Status. | The test has run for a time equal to KeHVLR_t_HVILOpenSamplesDurationTime |
| Invalid | The BPCM senses an invalid state of operation for the High Voltage Interlock Status. | The BPCM has detected an electrical fault with the HVIL circuit External or Internal to the battery (shorted High, Shorted Low) |

#### Diagnostics Associated with HVIL (Functional)
Diagnostics Associated with HVIL
| DTC Name |  |
| --- | --- |
| High Voltage System Interlock Circuit "A" | Battery Energy Control Module High Voltage System Interlock Circuit |
| High Voltage System Interlock Circuit "A" Low | Battery Energy Control Module High Voltage System Interlock Circuit Low |
| High Voltage System Interlock Circuit "A" High | Battery Energy Control Module High Voltage System Interlock Circuit High |
| High Voltage System Interlock Circuit "A" Performance |  |
When implementing diagnostics/DTCs keep in mind:
¡¤ The BPCM shall perform short-to-high, short-to-low and open circuit diagnostics on the external and internal HVIL line when the circuit is energized.
¡¤ The diagnostic to determine High Voltage Interlock Status shall be executed with at least a 100ms refresh rate (i.e. HVIL Fault should be detected in 100ms or less).

#### Calibrations Associated with HVIL (Functional)
Calibrations Associated with HVIL
The following internal BPCM calibrations shall be associated with HVIL. Calibrations marked with a default value can be hard-coded by the Teams.
| Calibration | Default Value | Unit/Type | Description |
| --- | --- | --- | --- |
| Ke_t_HVILShortSamplesDurationTime | 50 ms | Time (s) | The duration of time for which HVIL must be measured to diagnose a short |
| Ke_t_HVILOpenSamplesDurationTime | 50 ms | Time (s) | The duration of time for which HVIL must be measured as open. |
| Ke_t_HVIL_Dly_Tim* | 50 ms | Time (s) | The amount of time for which the HVIL Diagnostic will delay start to maturing post wake up |
| Ke_t_HVILOnTimeout* | 60 ms | Time (s) | Expiry Time before which HVIL needs to be energized on startup |
*Note: The default values listed for these calibrations are the recommended time durations within which HVIL should be sourced as per the wakeup timing table. If this time is not adequate to source HVIL, then it may be dependent on factors such as M450 initialization time and may have to be increased.

#### CAN Signals Associated with HVIL (Functional)
CAN Signals Associated with HVIL
| CAN Signal | Tx/Rx |
| --- | --- |
| HVBatIntrlk_InternalStat | Tx |
| HVBatIntrlkStat | Tx |

### Contactor Control (Functional)
Contactor Control
The battery voltage is separated from the propulsion high voltage bus by two normally open, single pole contactors.
The process for the closing and opening of the contactors can be summarized by the following: the vehicle controller sends a contactor command, the command is received by the BPCM, and the BPCM executes the command provided all the conditions for closing or opening the contactors are met.
The contactor closing and opening process includes, but is not limited to, the following algorithms: command validity determination, bus capacitive precharging, shorted bus detection, welded contactor detection, and isolation detection. Precharging and completing the circuit are both fundamental to ensure connection to the bus.
Teams should note that contactors have different DTC requirements than Breaktors. The DTC names listed below are assuming that teams use their Breaktors for the main contactors and DCFC. If a Team¡¯s configuration is different than that, they can refer to the DTC Matrix to find the applicable DTCs.

#### Contactor Control_1: Contactor Control (Functional)

##### High Voltage Battery Contactor Status (Functional)
High Voltage Battery Contactor Status
The value of the High Voltage Battery Contactor Status (HVBatCntctrStat) represents the driver state of the battery pack contactors at the time of signal transmission and is transmitted from the BPCM via CAN. The battery pack contains the negative main, positive main and precharge contactors.
HVBatCntctrStat shall be updated within two transmission cycles of the message containing it on the CAN bus. The potential values of the signal are described below:
| HV Battery Contactor Status | Status Requirements |  |
| --- | --- | --- |
| OPEN | · In this state, the Positive Main and Precharge contactors are de-energized because of any of the following items: · A transition from the CLOSED state · The commencement of an Operation Cycle (key on battery pack woken up from sleep) and BPCM Precharge Circuit Thermal Protection is DISABLED |  |
| PRECHARGING | The Negative Precharge Contactor(s) are energized |  |
| PRECHARGING | The Negative Precharge Contactor(s) are energized |  |
| CLOSED | · The Breaktor/Negative and Positive Main Contactors are energized |  |
| CLOSED | · The Breaktor/Negative and Positive Main Contactors are energized |  |
| PRECHARGE FAILED | · All contactors are OPEN due to any of the following items: · Remaining in PRECHARGING state for a continuous duration of time more than Ke_t_HighVoltageBusPrechargeTime · BPCM Disconnected HV Bus Detected transitioning from FALSE to TRUE (HVIL is open) · BPCM Precharge Current Too High Detected transitioning from FALSE to TRUE · A retry attempt within the PRECHARGING state |  |
| PRECHARGE FAILED | · All contactors are OPEN due to any of the following items: · Remaining in PRECHARGING state for a continuous duration of time more than Ke_t_HighVoltageBusPrechargeTime · BPCM Disconnected HV Bus Detected transitioning from FALSE to TRUE (HVIL is open) · BPCM Precharge Current Too High Detected transitioning from FALSE to TRUE · A retry attempt within the PRECHARGING state |  |
| PRECHARGE INHIBITED | · All contactors are de-energized because of BPCM Precharge Circuit Thermal Protection transitioning from DISABLED to ENABLED (cool down period for precharge resistor to cool down) |  |

##### Contactors Opening or Prevented from Closing (Functional)
Contactors Opening or Prevented from Closing
The BPCM shall report all reasons for the following actions:
¡¤ Not closing the contactors when commanded
¡¤ Not completing a precharge (further discussed in I-2)
¡¤ Opening contactors while they were commanded closed.
These strategies are defined in the DTC Matrix and DTCs shall be set accordingly. As an example, if the contactors open when commanded closed, the condition shall be able to be traced back to a unique DTC that signifies the reason for why the contactors opened.
If the contactors are inhibited from closing, the DTC shall not clear in the same key cycle, even if a loss of 12V occurs. Contactor inhibits and DTCs shall be cleared through service control routine.
Contactor closure can be further inhibited if internal and external HVIL are not passing. Additionally, the BPCM shall only prevent contactors from closing when in a faulted condition. When the faulted condition is gone and if all conditions are met to close contactors (e.g. contactor close is not inhibited), then the BPCM shall close contactors in the following key cycle.
On Vehicle Controller contactor command signal MainHighVltCntctrCmd = Fast Open, then BPCM shall open contactors immediately and not allow diagnostic checks (such as weld or isolation) to delay the open.

##### Contactor Control Circuit Diagnostics (Functional)
Contactor Control Circuit Diagnostics
The table below hosts the names for some of the above diagnostics. These are the names listed in the DTC Matrix. Teams should do their own verification to ensure they have implemented all necessary diagnostics, including other criteria like fault reactions. Additionally, there are multiple DTCs listed for the names below. Teams must keep the DTCs they implement unique.
| DTC Name |  |
| --- | --- |
| Main Breaktor Positive High Control Circuit/Open | Main Breaktor Negative Control Circuit/Open |
Another DTC that Teams must implement is associated with the HV Battery Contactor Status signal. The logic to set this DTC is as follows:
¡¤ At wake up, Battery Contactor Status shall initialize to the OPEN state.
¡¤ If the Battery Contactor Status is set to PRECHARGEINHIBIT, then the BPCM shall set the Diagnostic Trouble Code (DTC) to FAIL.
¡¤ Otherwise, the BPCM shall set the DTC to PASS. The specific DTC will be dependent upon the value of BPCM Disconnected Bus Detected.
In addition to the above DTCs, the BPCM shall internally store the Normal, Shorted Low, Shorted High, and Open states of both the Contactor Coil High Side State and Contactor Coil Low Side State. The states for both the High and Low Sides shall be stored and accessible via DID.

##### Contactor Stuck Open Diagnostics (Functional)
Contactor Stuck Open Diagnostics
The BPCM shall perform a series of contactor stuck open detection when the contactors have been commanded to close. The BPCM shall also store the status of the contactor stuck open for each contactor. These statuses shall be accessible via DID.
The table below hosts the names for some of the required diagnostics, as listed in the DTC Matrix. Teams should do their own verification to ensure they have implemented all necessary diagnostics, including other criteria like fault reactions
| DTC Name |  |
| --- | --- |
| Main Breaktor Positive Stuck Closed | Main Breaktor Negative Stuck Closed |
| Main Breaktor Positive Stuck Open | Main Breaktor Negative Stuck Open |
In addition to setting DTCs, Teams must ensure that the contactor closing sequence is inhibited or aborted if ANY of the contactors have been diagnosed with contactor stuck open conditions due to coil fault. If the BPCM detects a contactor stuck open, then HVBatCntrWeld_ImpdOpn = STUCK_OPEN.
The contactor closing sequence shall additionally desource HVIL if ANY of the contactors have been diagnosed with contactor stuck open conditions during a closing sequence.

##### Internal Variables and Calibrati: Internal Variables and Calibrations Associated with Main Contactor Control (Functional)
Internal Variables and Calibrations Associated with Main Contactor Control
The following internal variables and calibrations shall be used in main contactor control. Some calibrations have default values that teams may use. Teams should be aware that some of these default values, particularly in regard to timing, may still need to be changed to fit the Team’s architecture.
| Calibration | Default Value | Unit / Type | Description |
| --- | --- | --- | --- |
| Ke_t_BPCMContactorMaxDelayTime | TBD by Teams | Time (s) | This calibration is used by the BPCM as the overriding timer to get out of an impending open situation. |
| Ke_t_HighVoltageBusPrechargeTime | TBD by Teams | Time (s) | Indicates the amount of time in which the precharge function is expected to be complete. |
| Ke_I_ImpendingOpenLowBatteryCurrent | 5 | Current (A) | This calibration represents the amount of current that the BPCM considers to be low enough to open contactors when in an impending open situation. |
| Ke_I_PrechargeCurrentThreshold | Pack current ≥ 0.8 * (pack voltage / Precharge resistance) | Current (A) | This calibration represents the max current limit beyond which precharge should fail. |
| Ke_t_BPCMContactorLowCurrentTime | 1.5 | Time (s) | This calibration represents the amount of time the BPCM has observed Ke_I_ImpendingOpenLowBatteryCurrent or less battery pack current before it can open the contactors when in the impending open situation. |
| Ke_v_ContactorOpenControlledShutdownVehicleSpeed | 5 | Speed (km/h) | This calibration represents the vehicle speed at which the BPCM may open contactors in an impending open situation. |
| Ke_U_12VInputBPCMOverVoltage | 18 | Voltage (V) | This calibration represents the upper voltage threshold in which the BPCM will set the Request Open Command (HVBatCntctrReq / HVBatCntctrOpn) to Request Open. See section T-3 for further details. |
| Ke_U_12VInputBPCMUnderVoltage | 7 | Voltage (V) | This calibration represents the lower voltage threshold in which the BPCM will set the Request Open Command (HVBatCntctrReq / HVBatCntctrOpn) to Request Open. See section T-3 for further details. |
| Ke_T_HVBPMaxElementOverTemp | 60 | Temperature (C) | Indicates the maximum temperature that the BPCM will keep the contactors closed. |
| Ke_t_HVBPMaxElementOverTempTime | TBD by Teams | Time (s) | Indicates the time period that a high voltage battery pack element must exceed its over temperature threshold before the contactors are requested open. |
| Ke_t_CnctrCloseDebounce | 40 | Time (ms) | Indicates the amount of debounce time in which the contactor is forced to stay open once a OPEN TO CLOSE command is triggered. |
| Ke_ P_LimpRegenPwr | TBD by Teams | Power (kW) | Indicates allowed regenerative power in Limp Mode |
| Ke_ P_LimpDischargePwr | TBD by Teams | Power (kW) | Indicates allowed discharge power in Limp Mode |
| Internal Signal Name | Enumeration | Description |
| --- | --- | --- |
| Verified Contactor Command | OPEN CLOSED IMPACT OPEN INVALID | The Verified Contactor Command represents the BPCM’s interpretation of the contactor command received from the Vehicle Controller (as determined from either CAN Bus). This will be stored as an internal BPCM variable that can be observed via a DID or on the BPCM’s internal CAN. |
| Qualified Contactor Command | OPEN CLOSED IMPENDING OPEN EMERGENCY OPEN | The Qualified Contactor Command represents the BPCM’s internal determination of what the contactor command needs to be based on its own interpretation of the current state of the system. For example, if the BPCM determines that contactors need to be opened due to a diagnostic fault, the Verified Contactor Command from the vehicle might still be “CLOSED” but the Qualified Contactor Command should be “OPEN” |
| Precharge Current Too High | 0 – Not Too High 1 – Too High | Signal to detect if the precharge current is over a calibratable threshold (Ke_I_PrechargeCurrentThreshold). |

##### CAN Signals Associated with Main Contactor Control (Functional)
CAN Signals Associated with Main Contactor Control
Below is a table of the named CAN signals in this section of the SRD. This is not a comprehensive list of all CAN signals you may need.
| CAN Signal | Tx/Rx |
| --- | --- |
| HVBatCntctrStat | Tx |
| MainHighVltCntctrCmd | Rx |
| HVBatCntrWeld_ImpdOpn | Tx |

#### Precharge (Functional)
Precharge
Precharging the HV bus is defined as charging the HV bus voltage to a voltage that is within a predetermined voltage (calibratable, typically 95%) of the battery pack voltage in less than a predetermined amount of time. As such, the precharge relay shall be closed until the HV bus is charged.
Precharging the HV bus allows the battery pack voltage to be applied through the precharge resistor, which yields a ¡°ramped-in¡± voltage waveform and avoids an uncontrolled high current.

##### Precharge Initiation (Functional)
Precharge Initiation
The precharge process shall occur by closing the precharge contactors (positive and negative) after the BPCM has completed the wake-up procedure.
After determining that the Vehicle Controller is commanding the contactors closed, the BPCM shall precharge the HV bus when HVIL has been asserted and ALL the following are TRUE:
¡¤ HVIL continuity has been confirmed
¡¤ Qualified Contactor Command is equal to CLOSED
¡¤ Contactor close inhibit conditions are not present (Weld Check, Isolation etc.)
Once again, precharging only includes closing the precharge contactors. The main contactors/breaktor should remain open during this process.
Additionally, in the case that the high voltage bus sensor read by the BPCM is providing non-credible data, the signal HVInvRatVlt is supplied by the Vehicle Controller as a backup for precharge. It is the Vehicle Controller¡¯s measurement of the DC Propulsion Bus Voltage.

##### Precharge Complete Criteria (Functional)
Precharge Complete Criteria
To determine that precharge has been completed, the BPCM shall compare the battery pack voltage to the bus voltage, also called the link voltage. The link voltage shall be within a calibrated percentage of the pack voltage.
The battery current shall be monitored such that when the current does not decay, it is an indication that the High Voltage Propulsion Bus may have a short between its positive and negative terminals The internal variable (BPCM Shorted Bus Detected) is responsible for this—it shall indicate whether the current decays sufficiently during the precharge process of the High Voltage Propulsion Bus.
In the case that the BMS is using the DC Propulsion Bus Voltage for precharge, there is another signal, HVInvRatVltV, that acts as the vehicle controller’s determination of the validity of its DC Propulsion Bus Voltage. The BPCM uses this to decide if precharge can be completed and the positive main contactor can be closed.
To close the positive main contactor (i.e., to connect the main HV bus), the following conditions must be true:
· Vehicle Controller commands contactors to “CLS” (close) via MainHighVltCntrctrCmd
· Precharge is complete
The BPCM shall send the CAN signal HVBatCntctrStat (Battery Contactor Status), within the next two CAN samples. If the BPCM is unable to connect to the HV bus, the following shall be completed:
· The relevant DTC(s) shall be set TRUE determined by DTC matrix
· Precharge status shall be set to FAILED

##### Precharge Time-Out and Circuit Thermal Protection (Functional)
Precharge Time-Out and Circuit Thermal Protection
The BPCM shall terminate precharge if the precharge complete criteria has not been achieved after a prescribed time (Ke_t_HighVoltageBusPrechargeTime).
The BPCM shall allow sufficient time (Ke_t_BPCM_Precharge_Fail_Penalty_Time) for the precharge circuitry to cool before reattempting precharge. The BPCM shall also provide a countdown timer until next allowed attempt, through the Precharge Penalty Timer Prchrgpnltytimer. The Precharge Penalty Timer shall continue to count down independent of key position or wake/sleep state of the BPCM.
In the event of loss of 12V while the Precharge Penalty Timer is counting, BPCM shall restart the Precharge Penalty Timer after loss of 12V recovers. Once the Precharge Penalty Timer reaches zero, the BPCM shall attempt Precharge once the Main High Voltage Contactor Command = Close.
When a precharge inhibit is not active, the BPCM shall retry attempts to precharge until cool down period is needed (enabling of Precharge Thermal Protection), as determined by the Team. If precharge fails the second time, wait for a little longer (Ke_t_ExtraPrechargeFailCoolPenaltyTime). Continue this until precharge is either successful or inhibited. Precharge inhibit calculation is defined by adding a time (Ke_t_PrechargeFailCoolTime) for each attempt until it crosses a threshold (Ke_t_PrechargeFailMaxPenalty).
During the inhibit, the CAN signal HVBatCntctrStat shall indicate ¡°Precharge Inhibited.¡±
After failing multiple attempts in a row (when only milliseconds between each precharge attempt), the CAN signal HVBatCntctrStat shall indicate transition between PRECHARGE and PRECHARGE FAILED.

##### Precharge Diagnostics (Functional)
Precharge Diagnostics
The BPCM shall detect and communicate through DIDs or DTCs during the precharge sequence for diagnostics. If any of these situations are encountered, the BPCM shall follow the appropriate actions as defined in the DTC Matrix. The BPCM shall store to EEPROM the result of precharge diagnostics and all associated FOMs.
The table below hosts the names for some of the required diagnostics, as listed in the DTC Matrix. Teams should do their own verification to ensure they have implemented all necessary diagnostics, including other criteria like fault reactions.
| DTC Name |  |
| --- | --- |
| Hybrid/EV Battery System Precharge "A" Time Too Long | Hybrid/EV Battery System Precharge "A" Current Too High |
| HV Battery System Precharge Time Too Short |  |
¡¤ Note that ¡°Precharge Time Too Short¡± shall not set unless the starting link voltage is below a certain calibratable value (Ke_U_PrechargeDischargeLinkVoltage) when precharging to ensure the diagnostic does not falsely set in passive discharge conditions.

##### Internal Variables and Calibrati..._1: Internal Variables and Calibrations Associated with Precharge (Functional)
Internal Variables and Calibrations Associated with Precharge
The following internal variables and calibrations shall be used with Precharge and shall be accessible via DIDs.
However, teams still need to implement an algorithm to inhibit precharge after certain retries to prevent indefinite amount of retries. One thing to consider is the delay to reflect the correct temperature of the precharge resistor. If this delay is significant, teams can run into a scenario where a delay in temperature update can allow another precharging attempt and making system unsafe.
| Calibration | Default Value | Unit / Type | Description |
| --- | --- | --- | --- |
| Ke_n_FailedVoltageElementSensorFailNumber | TBD by Teams | Count | Represents the number of voltage sensors that must fail in the HV battery pack before the BPCM will set the High Voltage Battery Voltage Validity signal to invalid. |
| Ke_U_BusDisconnectThresholdVoltage | TBD by Teams | Voltage (V) | Represents the voltage threshold in which the propulsion bus voltage must be to have successfully performed a high voltage discharge. |
| Ke_t_HighVoltageBusPrechargeTime | TBD by Teams | Time (s) | Represents the amount of time that is allowed for precharging the HV bus (i.e. the amount of time the HV bus voltage must reach a predetermined voltage of the battery pack voltage). |
| Ke_I_HighVoltageBusShortageCurrent | Pack current ¡Ý 0.8 * (pack voltage / Precharge resistance) | Current (A) | The current as seen on a shorted bus during precharge. If current hasn¡¯t risen to within this level after contactors are reported closed, then the Vehicle Controller will command the contactors open. |
| Ke_t_PrechargeDetectedBusShortPeriod | TBD by Teams | Time (s) | The amount of time the BPCM will wait to see the high voltage battery current decay below 50% of its initial value. |
| Ke_t_CnctrCloseDebounce | 40ms | Time (s) | Indicates the amount of debounce time in which the contactor is forced to stay open once an OPEN TO CLOSE command is triggered. |
| Internal Signal | Unit / Type | Description |
| --- | --- | --- |
| BPCM Precharge Pack Voltage | Voltage (V) | Represents the voltage on the battery pack side of the contactors during precharge. It can differ from the signal that is transmitted via CAN as High Voltage Battery Pack Voltage. |
| BPCM Precharge Circuit Thermal Protection | Boolean | Identifies when the precharge contactor cannot be energized to prevent damage to the precharge circuitry (contactor status of precharge is inhibited). |
| BPCM Precharge Pack Voltage Source | Enumeration | Identifies the origin of the BPCM precharge battery pack voltage. |
| BPCM Bus Voltage | Voltage (V) | Represents the voltage measurement of the High Voltage Bus using the BPCM Bus Voltage Sensor located on the vehicle side of the High Voltage Battery Pack Contactors. This variable is different than the voltage measurement sent on the CAN bus. |
| Prchrgpnltytimer | Time (s) | Indicates the amount of time to allow precharge circuitry to cool before reattempting precharge. |
| BPCM Shorted Bus Detected | Boolean | Indicates whether the current decays sufficiently during the precharge process of the High Voltage Propulsion Bus |

##### CAN Signals Associated with Precharge (Functional)
CAN Signals Associated with Precharge
| CAN Signal | Tx/Rx |
| --- | --- |
| HVInvRatVlt | Rx |
| HVInvRatVltV | Rx |
| HVBatCntctrStat | Tx |
| MainHighVltCntctrCmd | Rx |

#### Contactor Weld Check Diagnostics (Functional)
Contactor Weld Check Diagnostics
The BPCM shall monitor the bus voltage after the contactors have been opened to ensure that the voltage drops when the contactors have opened.
The BPCM shall populate HVBatCntrWeld_ImpdOpn = STUCK_CLOSED whenever a welded contactor has been detected.
During shutdown, the BPCM shall check for individual contactor weld. The DTCs shall be set according to DTC Matrix on how individual weld checks will be completed.
The BPCM shall desource HVIL with an active contactor weld diagnostic.

##### Conditions When to Perform Contactor Weld Check (Functional)
Conditions When to Perform Contactor Weld Check
The BPCM shall perform a voltage-based weld check when Qualified Contactor Command has transitioned from CLOSED to OPEN.
The BPCM shall NOT perform a voltage-based weld check diagnostic if ANY of the following conditions are TRUE:
¡¤ Qualified Contactor Command is transitioning from IMPENDING OPEN to OPEN
¡¤ Qualified Contactor Command is OPEN while Vehicle Speed > Ke_v_WeldCheckEnableSpeed
¡¤ There is an impact (which will be communicated from the Vehicle Controller through the Contactor Command signal as IMPACT OPEN)
The BPCM shall be able to enable/disable the weld check diagnostic through the parameter Ke_b_WeldCheckEnabler using the following logic and this logic should only be used during development of the program and should be disabled in production:
¡¤ Ke_b_WeldCheckEnabler = 0 shall be interpreted as weld check diagnostic disabled
¡¤ Ke_b_WeldCheckEnabler = 1 shall be interpreted as weld check diagnostic enabled
¡¤ The Ke_b_WeldCheckEnabler shall be accessible through a DID.

##### Conditions to Interrupt Contactor Weld Check (Functional)
Conditions to Interrupt Contactor Weld Check
The weld check diagnostics should be interrupted in the following conditions:
¡¤ Insufficient 12V supply
¡¤ Controller RAM / ROM / EEPROM Error, Micro-controller failure detected
¡¤ BPCM observes HW Wakeup line transitions from Low to High
¡¤ Welded Contactor Error Storage
The BPCM shall store the status of the Weld Check through a DID and a DTC.
On shutdown the BPCM shall implement a retry strategy on the diagnostic with the following method.
1. Conduct a voltage-based welded contactor test during shutdown and if that passes, then proceed with a complete shutdown based on the Vehicle Controller command. Do not set a DTC in this case.
2. If the test from step 1 fails, wait long enough to allow for passive discharge on the bus to occur. Then repeat the welded contactor test and afterward, continue to shut down. This is both in the case that the welded contactor test passes or fails. Do not set DTC. Loss of 12V shall not erase the count of retry strategy.
3. Upon wake-up, if the welded contactor test before powering down failed, then re-do the test. If the test prior to power-down was passed, then continue the power-up sequence and do not set a DTC.
4. If, after wake-up, the welded contactor test still fails, then set weld DTC = TRUE.
Once the welded contactor fault is set to TRUE, the state of the BPCM welded contactor diagnostics shall be latched until reset by a service tool. Additionally, once the fault is set as active, loss of 12V shall not erase the fault status.

### Loss of Isolation Detection (Functional)
Loss of Isolation Detection
Loss of Isolation Detection (LOI) is an in-vehicle diagnostic function that detects the loss of galvanic separation between the HV circuits and chassis ground including LV circuits. The degree of LOI is controlled by regulatory requirements and industry standards. There are two isolation values that must be determined:
1. Isolation within the battery pack when the contactors are open
2. Isolation on the vehicle high voltage bus when the contactors are closed.

#### General Requirements for Loss of Isolation (LOI) (Functional)
General Requirements for Loss of Isolation (LOI)
All Isolation requirements and Isolation Monitoring/Testing requirements in FMVSS 305 shall supersede the requirements in this document.
The BPCM shall monitor the HV bus to determine that the chassis and HV bus are isolated from one another. If the BPCM determines the HV bus and chassis are not isolated, then the BPCM shall set the appropriate diagnostic and perform appropriate activities.
At the beginning of an Operation Cycle, the value of Isolation Status shall be initialized to the last recorded value in memory. The BPCM shall perform Isolation after weld check sequence is completed or aborted.
On the event that HVBatIsolStat has remained failed through power down, on the next key on (and subsequent key cycles) the contactors shall be inhibited from closing until cleared by a service routine. Once HVBatIsolstat has failed and fault is set as active, loss of 12V shall not erase the fault status.

#### Isolation Abort and Inhibit Requirement (Functional)
Isolation Abort and Inhibit Requirement
The BPCM shall abort Isolation Detection when ANY of the following is TRUE:
¡¤ Transition of HVIL Status to Failed
¡¤ Internal Isolation Circuitry has failed
¡¤ Contactors are undergoing closing or opening sequence
¡¤ When the BPCM receives the UDS $0308 Hybrid Battery HV - Isolation test, (in order to start the UDS routine) it shall first terminate the Isolation test that is underway and reset associated diagnostic variables to restart the test as commanded.
The BPCM shall inhibit Isolation Detection when ANY of the following is TRUE:
¡¤ Weld Check Contactor Faults are True
¡¤ HVIL Status is Failed

#### Isolation Status (Functional)
Isolation Status
The signals, HVBatIsolStat and PwrtrnHV_IsolStat, shall be used to indicate the status of isolation tests. HVBatIsolStat shall indicate the status of the open contactor isolation detection status. PwrtrnHV_IsolStat shall indicate the status of the closed contactor isolation detection status.
The BPCM shall set the Isolation Status CAN signals (HVBatIsolStat and PwrtrnHV_IsolStat) to Not Sourced (N_S) when it has not performed the isolation detection. This includes initialization, when contactors are Open, or during any BPCM hardware failures.
The value of Isolation Status shall only be changed/updated once a complete isolation test has been performed on the Battery Pack.
After performing the isolation test, the BPCM shall report the Isolation Status as either ¡°Pass¡± or ¡°Fail.¡±

#### Isolation Diagnostics (Functional)
Isolation Diagnostics
Diagnostic capability shall be able to determine the integrity of the Loss of Isolation circuitry. This diagnostic test shall not occur if the contactors are welded. All values of isolation and the statuses shall be available through diagnostic services via DIDs. Below is a non-comprehensive list of potential DTCs to include:
| DTC Name |
| --- |
| Hybrid Battery Voltage System Isolation Fault |
On the event that the powertrain isolation has failed, a service light shall persist through key cycles until cleared by a service tool.

#### Calibrations Associated with Isolation Detection (Functional)
Calibrations Associated with Isolation Detection
| Calibration | Default Value | Unit / Type | Description |
| --- | --- | --- | --- |
| Ke_R_IsolationFailResistanceLevel | 350 | kOhm | This calibration shall represent the minimum level of measured resistance on the DC bus, determined by using an AC isolation method, which must be observed to consider that the bus is in a PASS state of isolation. |

#### CAN Signals Associated with Isolation Detection (Functional)
CAN Signals Associated with Isolation Detection
| CAN Signal | Tx/Rx |
| --- | --- |
| HVIsolStat | Tx |
| PwrtrnHV_IsolStat | Tx |

### Impact response by the BPCM (Functional)

#### General Impact Response Requirements for BPCM (Functional)
General Impact Response Requirements for BPCM
Three impact threads shall be employed to ensure HV shuts down during an impact event:
1) Impact Message – BMS Optimal Thread. HCP transmits the ORC crash signal received through the Main High Voltage Contactor Command CAN message to the BMS
2) Impact Message – Direct Delayed Thread (Secondary Thread). BMS receives gated CAN ORC message through HCP.
3) Impact Message – Loss of Messages Thread. BMS assumes there was an impact due to no valid main contactor command message received on either primary or secondary CAN bus
The Occupant Restraint Component (ORC), HCP, and BMS strategies shall use the dual (redundant) CAN Bus to provide redundant communications.
The Impact Response shall not be evaluated when ignition is off or accessory (HCP_GW_20.CmdIgnStat = IGN_LOCK or HCP_GW_20.CmdIgnStat = IGN_OFF_ACC). The ORC module is not communicating in Ignition Status equal to Lock and Accessory, so there is no need to run diagnostics on the ORC under these conditions.
Teams should have their BMS receive HCP gated ORC signals on e-PT CAN busses. Under these conditions:
· In conditions with vehicle impact, BMS shall specify ImpactHardwire = Actuate and ImpactHardwireV = Fail_Not_Present.
· In conditions without a vehicle impact, BMS shall specify ImpactHardwire = Do_Not_Actuate and ImpactHardwireV = Fail_Not_Present.
Teams should note that the HCP gates impact crash signals come from the vehicle CAN to ePT CAN via IMPACT_INFO.IMPACTCommand and IMPACT_INFO.IMPACTConfirm. Under these conditions:
· In conditions without a vehicle impact, the IMPACT_INFO.IMPACTCommand = Do_Not_Actuate and IMPACT_INFO.IMPACTConfirm = Do_Not_Actuate signals shall specify the communication path is operational.
· In conditions with vehicle impact, the IMPACT_INFO.IMPACTCommand = Actuate and IMPACT_INFO.IMPACTConfirm = Actuate signals shall specify an impact has occurred. The BMS must receive both actuate signals for a confirmed impact.

#### Impact Response Development (Functional)
Impact Response Development
The BPCM shall provide the type of impact thread that occurred: Optimal, Direct Delayed, Loss of Message or No Impact.
The BPCM shall retain the type of impact thread that occurred in nonvolatile memory, however the CAV tema shall not be resetting each type of
Reset type of impact thread occurrence to No Impact.

#### Optimal Thread (Functional)
Optimal Thread
In conditions with a vehicle impact, the HCP shall initiate an impact open request via the Hybrid_Command_BPCM.MainHighVltCntctrCmd = Impact Open signal to specify an impact has occurred.
Upon receiving one valid sample of the Hybrid_Command_BPCM.MainHighVltCntctrCmd = Impact Open signal, the BMS shall set BPCM_MSG_01.HVBatCntctrReq = True and BPCM_MSG_01.HVBatCntctrOpn = True, set the corresponding Impact DTC (P167B) to be Active, and Open_HV_Contactors immediately without waiting any delay.
¡°Open_HV_Contactors¡± shall be defined as commanding all HV Contactors to mechanically open and the HV Bus external of the HVBS shall be galvanically separated from the HVBS cells and any internal power sources.
When detecting Impact via the Optimal Impact Response Thread, the BMS shall set ¡°Lockout_BMS_Contactor_Close_Operation¡±, which shall be defined as the BMS not allowing HV contactors to close unless a reset is provided by an external service tool.

#### Direct Delayed Thread (Functional)
Direct Delayed Thread
In conditions with a vehicle impact, the HCP shall initiate an impact open request by gating messages from the ORC via the IMPACT_INFO.ImpactCommand = Actuate and IMPACT_INFO.ImpactConfirm = Actuate signals to specify an impact has occurred.
Upon receiving four valid samples of IMPACT_INFO.ImpactCommand = Actuate and IMPACT_INFO.ImpactConfirm = Actuate signals, the BMS shall set BPCM_MSG_01.HVBatCntctrReq = True and BPCM_MSG_01.HVBatCntctrOpn = True, set the corresponding Impact DTC (P167B) to be Active, and Open_HV_Contactors within the short delay reaction timer (default = 1500ms).
When detecting Impact via the Direct Delayed Impact Response Thread, the BMS shall set ¡°Lockout_BMS_Contactor_Close_Operation¡±, which shall be defined as the BMS not allowing HV contactors to close unless a reset is provided by an external service tool.

#### Loss of Message Thread (Functional)
Loss of Message Thread
The BMS upon not receiving a valid HCP main contactor command on ePT CAN (Hybrid_Command_BMS) for duration of time as specified by ¡°BMS_Loss_of_Message_Timer¡± calibration (Ee_Impact_Loss_Of_Comm_Detection), default value of which shall be 1000ms, the BMS shall assume that an impact event has occurred.
An invalid HCP main contactor command on ePT CAN shall be defined as, on both Primary AND Secondary CAN, receiving message with incorrect CRC or MC, not receiving a message (Loss Of Communication), or detecting a Bus Off condition (CAN line shorted or open).
Upon reaching the ¡°BMS_Loss_of_Message_Timer¡± time, the BMS shall set BPCM_MSG_01.HVBatCntctrReq = True and BPCM_MSG_01.HVBatCntctrOpn = True, set the corresponding Impact DTC (P167B) to be Active, and Open_HV_Contactors within the short delay reaction timer (default = 1500ms).
When detecting Impact via the Loss of Message Impact Response Thread, the BMS shall set ¡°Lockout_BMS_Contactor_Close_Operation¡±, which shall be defined as the BMS not allowing HV contactors to close unless a reset is provided by an external service tool.
The Loss of Message Thread shall be evaluated 7.0 s after ignition key is in either run or start (HCP_GW_20.CmdIgnStat = IGN_RUN or IGN_START).

#### Impact Diagnostics (Functional)
Impact Diagnostics
The BMS shall have a routine to clear impact faults.
| DTC Name |
| --- |
| Controlled System Shutdown (note that this has multiple implementations) |
See referenced documents for additional diagnostic requirements.

#### Calibrations Associated with Isolation Detection_1: Calibrations Associated with Isolation Detection (Functional)
Calibrations Associated with Isolation Detection
| Calibration | Default Value | Unit / Type | Description |
| --- | --- | --- | --- |
| DTC fault reactions (ASW and BSW) | Varies by calibration | TBD by teams | Teams must make all DTC fault reactions calibratable via dedicated interfaces. Default values shall be set by the OBD calibration team. As an example: The timer value from when BPCM_MSG_01.HVBatCntctrReq = True to when contactors open under an impact condition shall be 1500ms (with the exception of the Optimal Thread which shall be an immediate open reaction |

#### CAN Signals Associated with Isolation Detection_1: CAN Signals Associated with Isolation Detection (Functional)
CAN Signals Associated with Isolation Detection
| CAN Signal | Tx/Rx |
| --- | --- |
| HVBatCntrtrReq | Tx |
| ImpactCommand | Rx |
| ImpactConfirm | Rx |
| HVBatCntctrOpn | Tx |
| CmdlgnStat | Rx |
| ImpactHardwire | Tx |
| ImpactHardwireV | Tx |

### Battery Conditioning (HVBatRdy) (Functional)
Battery Conditioning (HVBatRdy)
The signal, HVBatRdy, will be sent from the BPCM indicating to the vehicle whether the HV battery is ready to deliver/receive power or not.
If the signal is set to 0, this will indicate that the HV battery is not ready due to extremely hot or cold battery temperatures and/or high or low cell voltages. The contactors will still close to allow a small amount of power to heat or cool the battery, or raise or lower the voltage. Teams should refer to the charge/discharge power limits and max charge current allowed to determine what this small allowance of power is.
Between initialization and contactors closing, the value for the HVBatRdy signal shall be determined. The HVBatRdy determination for zero shall only be made during the initialization time.
HVBatRdy shall be set to zero in the following conditions. In these conditions, the BPCM shall allow contactors to close and not set a DTC.
· HVBatCellVltMax is above HVBatCell_Voltage_High_Thrsh
· HVBatCellVltMin is below HVBatCell_Voltage_Low_Thrsh
· HVBatModuleTemp_Max is above HVBatHighTempThrsh
· HVBatModTempMin is below HVBatLowTempThrsh
· Otherwise, HVBatRdy = 1.
Any other faults present which are not related to the HVBatRdy function and would either open the contactors or not allow the contactors to close shall still be allowed to perform their required action independent of the value of HVBatRdy.
If HVBatRdy is equal to 0 and DriveReady is equal to 1, the BPCM shall open contactors to protect the battery pack. When the conditions which made HVBatRdy = 0 are no longer true, with an appropriate amount of hysteresis, then HVBatRdy shall transition to 1 and continue to be 1 until the next wake-up/initialization. That is, once HVBatRdy status sets as 1, the BPCM shall not change the HVBatRdy status to 0 in the same key cycle.
The hysteresis for each condition to transition from HVBatRdy = 0 to HVBatRdy = 1 shall be defined as follows:
· Low cell voltage: HVBatCellVltMin is x volts above HVBatCell_Voltage_Low_Thrsh (calibratable, default = 0.1 V) and HVBatSOC is greater than the minimum charge sustaining value (calibratable, default: 15%)
· High cell voltage: HVBatCellVltMax is below HVBatCell_Voltage_High_Thrsh by at least x volts (calibratable, default: 0.1 V)
· High module temperature: HVBatModTempMax is below HVBatHighTempThrsh by at least x deg C (calibratable, default: 0.5 deg C)
· Low module temperature: HVBatModTempMin is above HVBatLowTempThrsh by at least x deg C (calibratable, default = 0.5 deg C)

#### Calibrations Associated with HVBatRdy (Functional)
Calibrations Associated with HVBatRdy
| Calibration | Default Value | Unit / Type |
| --- | --- | --- |
| Volts that HVBatCellVltMin is above HVBatCell_Voltage_Low_Thrsh. | 0.1 V | Voltage (V) |
| Minimum charge sustaining value | 15% | % |
| Volts that HVBatCellVltMax is below HVBatCell_Voltage_High_Thrsh | 0.1 V | Voltage (V) |
| Degrees C that HVBatModTempMin is above HVBatLowTempThrsh. | 0.5 deg C | Deg C |
| Degrees C that HVBatModTempMax is below HVBatHighTempThrsh. | 0.5 deg C | Deg C |

#### Battery Pack Conditioning CAN Signals (Functional)
Battery Pack Conditioning CAN Signals
| CAN Signal | Tx/Rx |
| --- | --- |
| HVBatRdy | Tx |
| HVBatCellVltMax | Tx |
| HVBatCellVltMin | Tx |
| HVBatModuleTemp_Max | Tx |
| HVBatModTempMin | Tx |
| HVBatCell_Voltage_High_Thrsh | Tx |
| HVBatCell_Voltage_Low_Thrsh | Tx |
| HVBatHighTempThrsh | Tx |
| HVBatLowTempThrsh | Tx |
| DriveReady | Rx |

### Sensor Measurements (Functional)
Sensor Measurements
For this section, all CAN signals are gathered at the end.

#### Current Measurement (Functional)
Current Measurement
The BPCM shall measure and communicate over CAN the current in and out of the battery pack assembly, which has a default sample time of 20ms.
The battery pack current shall report 0A on vehicle CAN when the contactor is open and no faults are present.
Redundancy in current measurements shall be required for rationality checks and the BMS shall have redundant current sensors inside the battery pack. The raw/unfiltered values of all current sensors shall be available over a private CAN bus from the BPCM (to be used during vehicle development).

##### Current Measurement Diagnostics (Functional)
Current Measurement Diagnostics
The current sensor diagnostics shall include the conditions of out of range, high, low, and rationality checks. Additionally, the raw/unfiltered value of the battery pack current DIDs shall be the same value read by the battery current sensors.
The validity of the current measurement shall be communicated over CAN. BPCM pack current validity shall be set to INVALID (BPCM internal validity) when ANY of the following is TRUE:
¡¤ BPCM pack current is abnormal (e.g., current sensor failure) BPCM abnormal (e.g., RAM/Stack or EEPROM Microcontroller failure)
¡¤ Otherwise, BPCM pack current validity shall be set to VALID

#### Voltage Measurement (Functional)

##### Battery Pack Voltage Measurement (Functional)
Battery Pack Voltage Measurement
The battery pack voltage shall be measured before the main contactor on the battery side. The BPCM shall have the sum of the cell voltages available as an internal variable for rationality and substitution for the battery pack voltage. The value of the sum of the cell voltages shall be accessible via a DID.
The battery pack voltage diagnostics shall include the conditions of out of range high and low and rationality checks. The value of the battery pack voltage shall be determined from the following priority:
¡¤ Valid Sum of Cell/Module Voltages
¡¤ Valid Pack Voltage Measurements
¡¤ Invalid if none of the measurements are available.
The value of the battery pack voltage source shall be determined from the following priority:
¡¤ CELL_SUM if through Valid Sum of Cell/Module Voltages
¡¤ SENSOR if through Valid Pack Voltage Measurements
¡¤ NONE if Invalid

##### Battery Pack Link Voltage (Functional)
Battery Pack Link Voltage
The battery pack link voltage shall be measured after the main contactor on the vehicle side of the high voltage bus. The value of the battery pack link voltage shall be determined from the following priority:
¡¤ Valid link voltage sensor measurement
¡¤ Combination of other rationalized high voltage measurements (e.g. other HV component sensing element A, B, C and D)
¡¤ Invalid if none of the measurements are available.
The value of the battery pack voltage source shall be determined from the following priority:
¡¤ LINK_SENSE if through Valid link voltage sensor measurement
¡¤ ELEMENT (A, B, C or D) if through Combination of other rationalized high voltage measurements
¡¤ NONE if Invalid
The value of the battery pack link voltage and its source shall be accessible via a DID. The value of the link voltage shall be available over a private CAN bus from the BPCM.

##### Additional High Voltage Measurements (Functional)
Additional High Voltage Measurements
Additional High Voltage measurements shall be available to properly support diagnostics (e.g. DC Fast Charging voltage sensors, contactor weld check voltage sensors, ¡­).
The values of the additional high voltage measurements shall be accessible via a DID. The values of the additional high voltage measurements shall be available over a private CAN bus from the BPCM (to be used during vehicle development).

##### Module Voltages (Functional)
Module Voltages
Module voltages, defined as a group of cells measured on the same ASIC, shall be measured and accessible via a DID.
A module¡¯s voltage shall be considered VALID when all the DTC¡¯s (e.g., diagnostics for element voltage sensors shorted to ground, shorted to battery, and rationality) are set to either NOT TESTED or PASS. Otherwise, the modules voltages shall be considered INVALID.
The sum of modules shall be INVALID if one of the module voltages is INVALID.
The BPCM shall have the sum of the module voltages available as an internal variable for rationality and substitution for the battery pack voltage. The value of the sum of the modules shall be accessible via a DID. The values of the module voltages shall be available over a private CAN bus from the BPCM (to be used during vehicle development).

##### Cell Voltages (Functional)
Cell Voltages
The BPCM shall measure the voltage of every cell/cell block and report battery pack voltage and the cell minimum, maximum, and average voltages over CAN on the vehicle network. Note that a cell block is a group of parallel cells. The cell locations (cell number) for the minimum and maximum cell voltages shall be communicated over CAN.
The measurement of the cell voltages shall be synchronized with the current within the specification of microprocessor ability. Bus bars and any other wiring that significantly affects the voltage measurements shall be compensated for.
All the cell voltages shall be accessible via a DID. The BPCM shall also keep a lifetime history, accessible via a DID, of at least the top 3 cells voltages that were high and the top 3 cells that were low, including the position identification of the cells. Can update NVM during shutdown.
The cell voltage sensor diagnostics shall include the conditions of out of range high and low and rationality checks. The rationality checks shall include cell summation and comparison with other available voltage measurements. Below are the names for the out of range DTCs.
| DTC Name |  |
| --- | --- |
| Hybrid/EV Battery Pack Cell Voltage High | Hybrid/EV Battery Pack Cell Voltage Low |

#### Temperature Measurement (Functional)
Temperature Measurement
The term, cell temperature, is used to denote the temperature that is used for temperature compensation of the Team¡¯s algorithms and the associated diagnostics.
The BPCM shall measure the temperature of every cell that is determined to be needed as a result of DFMEA, SOC/SOH algorithm support, or other engineering analyses (locations to be described and specified by the Team). The minimum, maximum, and average cell temperatures and the corresponding cell locations shall be reported over CAN on the vehicle network.
On initialization, the validity bits for the minimum, maximum and average cell temperatures shall indicate VALID (validity bit = 0) within 100 ms of communication. Once accurate temperatures are communicated, the validity bits shall stay VALID (validity bit = 0) and the signal validity should be INVALID (Validity bit = 1) only when both the inputs are unavailable and the sensor faults are confirmed.
All temperatures and pertinent thermal management parameters shall be available through service diagnostics via DIDs. The BPCM shall keep a lifetime history of at least the 3 top highest cell temperatures and the 3 lowest cell temperatures, including their positions within the battery pack. Can update NVM during shutdown. These values shall be accessible via a DID.
The BPCM shall also measure and report the temperatures of the cooling inlet and outlet (either liquid or air, whichever is applicable) and any other temperatures that need to be measured to implement the thermal management algorithms.
The BPCM shall measure and report the temperature of any other battery pack component that is essential for reliable operation (e.g., the CPU, balancing boards, precharge circuitry, etc.). These values shall be accessible via a DID.
The cell temperature and inlet and outlet sensor diagnostics shall include the conditions of out of range high and low and rationality checks.
All temperature measurements shall be available over a private CAN bus from the BPCM (to be used during vehicle development).

#### Cell Voltage and Temperature Thresholds (Functional)
Cell Voltage and Temperature Thresholds
The BPCM shall send the following cell voltage and temperature thresholds to indicate to the vehicle controller that the values are outside the normal region.
The strategy for how these thresholds may change with conditions (temperature, SOC, diagnostic status, plug-in charging, etc.) shall be documented by the Team and submitted to Competition Organizers for approval.
| Threshold | Default Value | Description |
| --- | --- | --- |
| HVBatLowTempThrsh | -29 degC | Signal from the BPCM indicating the value that the minimum module temperature needs to be above in order to become functional. Below this value, the BPCM will set HVBatCntctrReq to 1, and HVBatCntctrOpn to 1 after the appropriate maturation time. If below this value during power up, HVBatRdy will also be set to 0. |
| HVBatHighTempThrsh | 60 degC | Signal from the BPCM indicating the value that the maximum module temperature needs to be below in order to become functional. Above this value, the BPCM will set HVBatCntctrReq to 1, and HVBatCntctrOpn to 1 after appropriate maturation time. If above this value during power up, HVBatRdy will also be set to 0. |
| HVBatCell_Voltage_Low_Thrsh | 3V | Signal from the BPCM indicating the minimum cell voltage that the battery pack needs to be above in order to become functional. Below this value, the BPCM will set HVBatCntctrReq to 1, and HVBatCntctrOpn to 1 after appropriate maturation time. If below this value during power up, HVBatRdy will also be set to 0. |
| HVBatCell_Voltage_High_Thrsh | if (< 35 degC): 4.15 else (> 35 degC): 4.125 | Signal from the BPCM indicating the maximum cell voltage that the battery pack needs to be below in order to become functional. Above this value, the BPCM will set HVBatCntctrReq to 1, and HVBatCntctrOpn to 1 after appropriate maturation time. If below above this value during power up, HVBatRdy will also be set to 0. |
| HVBatMinCellVltAlld | if (< 35 degC): 4.15 else (> 35 degC): 4.125 | The minimum allowed cell voltage during operation. It is considered an extreme abnormality to exceed this value. |
| HVBatMaxCellVltAlld | if (< 35 degC): 4.15 else (> 35 degC): 4.125 | The maximum allowed cell voltage during operation. It is considered an extreme abnormality to exceed this value. |

#### Cell Voltage and Temperature Sensor Diagnostics (Functional)
Cell Voltage and Temperature Sensor Diagnostics
The limits for the voltage and temperature sensors shall be divided into 7 regions (see Figure below). Each of these regions has lifetime timers associated with them (a total of 7 lifetime timers for this implementation).
The temperature and voltage sensor values within region 4 shall be termed as a region of normal operation.
Voltage and temperature sensor operating limits within regions 1 and 7 shall be termed as a hardware fault which could be due to short to reference high or short to reference low. Each of these conditions shall have a DTC associated with it.
Voltage and temperature sensor output voltage limits within the regions 2, 3, 5, and 6 that exceed calibration timer values (0-10 seconds) shall take the appropriate action defined in the DTC Matrix.
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
#### CAN Signals Associated with Sensor Measurements (Functional)
CAN Signals Associated with Sensor Measurements
Any invalid sensor measurement shall report as SNA to indicate its measurement is not considered to be valid instead of the measured value.
| CAN Signal | Tx/Rx | Description |
| --- | --- | --- |
| HVBatteryCurrent_BEV | Tx | Battery pack current and its associated validity |
| HVBatteryVoltage_BEV | Tx | Battery pack voltage and its associated validity |
| HVBatCellVltAvg | Tx | Average cell voltage |
| HVBatCellVltAvgV | Tx | Average cell voltage validity (related to HVBatCellVltAvg) |
| CellVoltage_NumMin_BEV | Tx | Minimum cell voltage and its associated validity |
| CellVoltage_NumMax_BEV | Tx | Maximum cell voltage and its associated validity |
| HVBatModuleTemp_Max | Tx | Maximum cell temperature in the battery pack array of cell temperatures and its associated validity |
| HVBatModTempMin | Tx | Minimum cell temperature in the battery pack array of cell temperatures |
| HVBatModTempMinV | Tx | Associated validity of the above signal |
| HVBatModTempAvg | Tx | Average of all cell temperatures in the battery pack array of cell temperatures |
| HVBatModlTempAvgV | Tx | Validity of the average of all cell temperatures in the battery pack array of cell temperatures (related to HVBatModTempAvg) |
| HVBatClgInletTemp | Tx | The temperature of the inlet of the cooling medium |
| HVBatClgInletTempV | Tx | The validity of the temperature of the inlet of the cooling medium (related to HVBatClgInletTemp) |
| HVBatClgOutletTemp | Tx | The temperature of the outlet of the cooling medium |
| HVBatClgOutletTempV | Tx | The validity of the temperature of the outlet of the cooling medium (related to HVBatClgOutletTemp) |
| HVBatModuleTemp_NumMax | Tx | Cell temperature sensor position which has maximum temperature |
| HVBatModuleTemp_NumMin | Tx | Cell temperature sensor position which has minimum temperature |

### Plug-In Charging (Functional)

#### Plug-In Charging Algorithms (Functional)
Plug-In Charging Algorithms
The plug-in charging algorithm shall be explained and documented by the Team. The algorithm shall include, but not be limited to, dependencies on temperature, voltage, current, battery age, and diagnostic status. The plug-in charging algorithm shall comprehend charge power supplies at the 1.0 kW, 11.0 kW, and 0.5C rates.

#### Plug-In Charger Control (Functional)
Plug-In Charger Control
The proper voltage and current limits shall be communicated over CAN to allow the selected charger to properly charge the battery pack in an efficient and reliable manner.

#### CAN Messages and Signals Associa: CAN Messages and Signals Associated with AC and DC Fast Plug-In Charging (Functional)
CAN Messages and Signals Associated with AC and DC Fast Plug-In Charging
| CAN Signal | Tx/Rx | Description |
| --- | --- | --- |
| ChargingSysSts | Rx | This signal comes from the Vehicle Controller and indicates the status of the charging function |
| HVBatMaxCellVltAlld | Tx | This signal is sent out by the BPCM to the Vehicle Controller to indicate the maximum allowable cell voltage during charge. |
| HVBatMaxPkVltAllwd | Tx | This signal is sent out by the BPCM to the Vehicle Controller to indicate the maximum allowable battery pack voltage during charge. |
| HVBatChargeStat | Tx | This signal is sent out by the BPCM as an indication of its present status |
| DC_Isolation_Cmd | Rx | Isolation Disabling command for DC charging |
| DC_Isolation _Sts | Tx | Isolation status for DC charging |
| DC_CntctrCmd | Rx | High voltage battery DC contactor command |
| HVBat_DC_CntctrStat | Tx | HV Battery pack DC contactor state |
| HVBat_DC_CntctrOpn | Tx | HV Battery Pack DC contactor Open |
| HVBatCntctrReq | Tx | HV Battery pack contactor request |

#### AC Plug-In Charging Procedure (Functional)
AC Plug-In Charging Procedure
Initially, the contactors are not closed, and the signal HVBatChargeStat shall be equal to Not Ready.
Once a plug in is determined by the Vehicle Controller, contactors will be commanded closed and transition HVBatChargeStat = Ready. If the main contactors are closed, the battery shall continually acknowledge that it is ready for charge by setting HVBatChargeStat = Ready. If the battery should not or cannot be charged, the status of HVBatChargeStat = Not Ready.
If the Vehicle Controller determines that it is time to charge, ChargingSysSts will transition to ¡°charging¡±. During this phase, the BPCM shall populate MaxChargeCurrentAllowed with the max plugin charge current allowed to charge the HV battery (a calibratable value with default = 30A).
The battery shall enable any routines that pertain to charging only and prepare for charge and over-charge protection. When in charge mode, the charge power limits for regen will be based on HVBatCell_Voltage_High_Thrsh used during plug-in charge.
The charging handshake must also take place. That is, confirming that ChargingSysSts = Charging and HVBatChargeStat = Ready.
Once contactors are closed and the handshake has taken place, the battery shall transition into one of the following states:
¡¤ MaxChargeCurrentAllowed is equal to the max plugin charge current allowed to charge the HV battery.
¡¤ If the battery needs to cool or heat, then MaxChargeCurrentAllowed is a reduced value or 0 A
¡¤ If charging has completed (according to BPCM charge completion criteria and retry count), then HVBatChargeStat = Complete
The BPCM shall continually calculate and update the signals HVBatMaxCellVltAlld, MaxChargeCurrentAllowed, and HVBatMaxPkVltAllwd based on battery cell chemistry and communicate these to the Vehicle Controller. The Vehicle Controller will continuously monitor the cell voltage, current, pack voltage, and temperature.
If the temperature goes above Ke_T_HighChrgTempThresholdIn (default: 50 deg C) or if the temperature goes below Ke_T_LowChrgTempThresholdIn (default: = - 25 deg C), MaxChargeCurrentAllowed shall equal 0.
Once the temperature falls below Ke_T_HighChrgTempThresholdOut (default: 48 deg C) or the temperature increases above Ke_T_LowChrgTempThresholdOut (default: -23 deg C) MaxChargeCurrentAllowed shall be > 0.
The BPCM shall indicate to the Vehicle Controller when it is fully charged at a charge level set higher than the Vehicle Controller (calibratable: Ke_U_ChargeCompletionVlt, 4.14V (example), for at least 300 ms) by setting MaxChargeCurrentAllowed = 0.
The teams shall provide a table of temperature range and MaxChargeCurrentAllowed for both AC charging and DC Fast Charging and not to exceed other vehicle side components.
An example of the table is show below:
| SOC (%) / Temp (C) | -25 | -20 | -10 | 0 | 5 | 10 | 20 | 25 | 35 | 40 | 50 |
| --- | --- | --- | --- | --- | --- | --- | --- | --- | --- | --- | --- |
| 5 | 12 | 15 | 20 | 30 | 30 | 30 | 30 | 30 | 30 | 30 |  |
| 10 | 12 | 14 | 20 | 30 | 30 | 30 | 30 | 30 | 30 | 30 |  |
| 15 | 11 | 14 | 20 | 30 | 30 | 30 | 30 | 30 | 30 | 30 |  |
| 20 | 11 | 14 | 20 | 30 | 30 | 30 | 30 | 30 | 30 | 30 | 30 |
| 25 | 10 | 13 | 20 | 30 | 30 | 30 | 30 | 30 | 30 | 30 | 30 |
| 30 | 8 | 12 | 20 | 30 | 30 | 30 | 30 | 30 | 30 | 30 | 30 |
| 35 | 7 | 12 | 20 | 30 | 30 | 30 | 30 | 30 | 30 | 30 | 30 |
| 40 | 7 | 12 | 20 | 30 | 30 | 30 | 30 | 30 | 30 | 30 | 30 |
| 45 | 7 | 11 | 20 | 30 | 30 | 30 | 30 | 30 | 30 | 30 | 30 |
| 50 | 7 | 11 | 20 | 30 | 30 | 30 | 30 | 30 | 30 | 30 | 30 |
| 55 | 6 | 11 | 20 | 30 | 30 | 30 | 30 | 30 | 30 | 30 | 30 |
| 60 | 5 | 10 | 19 | 30 | 30 | 30 | 30 | 30 | 30 | 30 | 30 |
| 65 | 5 | 9 | 19 | 30 | 30 | 30 | 30 | 30 | 30 | 30 | 30 |
| 70 | 4 | 8 | 15 | 25 | 28 | 30 | 30 | 30 | 30 | 30 | 30 |
| 75 | 4 | 6 | 12 | 19 | 21 | 23 | 30 | 30 | 30 | 30 | 30 |
| 80 | 3 | 5 | 8 | 14 | 15 | 20 | 25 | 30 | 30 | 30 | 30 |
| 85 | 3 | 4 | 7 | 10 | 12 | 12 | 20 | 25 | 25 | 26 | 27 |
| 90 | 2 | 3 | 5 | 6 | 8 | 8 | 15 | 20 | 22 | 25 | 26 |
| 95 | 2 | 2 | 3 | 3 | 4 | 4 | 10 | 15 | 20 | 22 | 24 |

##### Calibrations Associated with AC Plug-in Charging (Functional)
Calibrations Associated with AC Plug-in Charging
| Calibration | Default Value | Unit / Type | Description |
| --- | --- | --- | --- |
| Max plugin charge current | 30 | A | The maximum plugin charge current allowed to charge the HV battery. |
| Ke_T_HighChrgTempThresholdIn | 50 | degC | Upper Threshold for Charge Temperature |
| Ke_T_LowChrgTempThresholdIn | -25 | degC | Lower Threshold for Charge Temperature |
| Ke_T_HighChrgTempThresholdOut | 48 | degC | Upper Threshold for Charge Temperature |
| Ke_T_LowChrgTempThresholdOut | -23 | degC | Lower Threshold for Charge Temperature |
| Ke_U_ChargeCompletionVlt | 4.14 | V | Held for at least 300ms, this is the charge level that the BPCM compares its charge to in order to indicate when it is fully charged. |

#### DC Fast Charge Plug-In Charging Procedure BEV (Functional)
DC Fast Charge Plug-In Charging Procedure BEV
Direct Current Fast Charging (DCFC) provides direct current (DC) to the EV battery by the inversion of a 3-phase 480 volt AC supply. DCFC (known as Level 3 charging) as part of public infrastructures, requires special BPCM software protections to ensure a robust charging event.
Upon making a connection with the DCFC Station, the following steps must take place:
1. Main contactors are open and the signal HVBatChargeStat shall be equal to Not Ready.
2. Main contactors will be commanded closed, and the BPCM shall close contactors and transition HVBatChargeStat = Ready.
3. Once a ¡°DCFC plug in¡± is determined by the vehicle controller, the BPCM shall disable its continuous isolation detection monitoring immediately, when it receives DC_Isolation_Disable_Cmd = 1.
4. The BPCM shall set DC_Isolation_Disable_Sts = DISABLE, when it successfully disables the continuous isolation detection.
5. The BPCM shall run its continuous isolation detection whenever:
a. DC_Isolation_Disable_Cmd = 0 and provide isolation detection status when DC_Isolation_Disable_Sts = ENABLE.
Afterwards, the following steps are taken:
1. The DCFC contactors are commanded closed through DC_CntctrCmd = CLS by the vehicle controller, and once receiving DC_CntctrCmd = CLS, the BPCM shall provide the DCFC contactors status through HVBat_DC_CntctrStat = Closed.
2. The BPCM shall indicate if the DCFC contactors are open through HVBat_DC_CntctrStat = Open.
3. If the Vehicle Controller determines that it is time to charge, ChargingSysSts will transition to ¡°charging¡±. During this phase, the BPCM shall populate MaxChargeCurrentAllowed_High = calibratable value based on its DCFC current profile.
a. If the BPCM detects a critical failure during charging, a diagnostic code shall be set and HVBat_DC_CntctrOpn = 1 notifying the vehicle controller that the DCFC contactors will open in a calibrated amount of time (Ke_t_DCFC CntctrOpn default: 1500 ms).
4. Since DCFC contactors are closed and charging hand shake has taken place (HVBatChargeStat = Ready, DC_Isolation_Disable_Sts = DISABLE , HVBat_DC_CntctrStat = Closed, and ChargingSysSts = Charging), the battery shall transition into one of the following states:
a. MaxChargeCurrentAllowed_ High > 0
b. If the battery needs to cool or heat MaxChargeCurrentAllowed_High = reduced value or 0 A
c. If charging has completed (according to BPCM DCFC completion criteria) HVBatChargeStat = Complete
5. Once the vehicle controller has determined charge complete, DC_CntctrCmd = OPN and BPCM shall open DCFC contactors and publish HVBat_DC_CntctrStat = Open.
a. If the BPCM detects a DCFC contactor failure, such as a weld or driver circuit fault, then the BPCM shall set HVBat_DC_CntctrStat = Faulted and publish a corresponding diagnostic code.
b. If the BPCM detects a DCFC contactor weld then the BPCM shall set HVBatCntctrReq = 1 and HVBatCntctrOpn = 1, then proceed to open the contactors in 1.5 seconds, inhibit main contactor closure and not source HVIL throughout all key cycles.

### (Optional) Cell Balancing (Functional)
(Optional) Cell Balancing
For this competition, implementing cell balancing is optional. Teams will be required to make sure their cells and modules are balanced at various stages of integration into their pack, but this feature will not be tested.

#### General Cell Balancing Requirements (Functional)
General Cell Balancing Requirements
Cell balancing is the process of equalizing the voltages and state of charge among the cells when they are at full charge. Passive Cell balancing removes the additional charge available in the higher SOC cells, by dissipating heat through the bleed resistors. This allows charging all the cells to the same 100% SOC, thereby maximizing the available energy at top of charge.
The BPCM shall allow balancing of individual cells only when any one of the following is TRUE:
¡¤ The BPCM is in autonomous balancing state AND autonomous balancing is enabled
¡¤ When in Key in Ignition or plug-in charging mode
Autonomous balancing shall only be enabled if approved. The Team shall meet the following conditions if Autonomous balancing has been enabled:
¡¤ The BPCM shall not wake up other vehicle controllers in the system (via CAN or hardwired)
¡¤ The BPCM shall not draw 12V power throughout the duration of the autonomous balancing (i.e. no parasitic 12V draw).

#### Cell Balancing Diagnostics and Protection (Functional)
Cell Balancing Diagnostics and Protection
The BPCM shall be able to distinguish between cells that are out of balance and cells that are failing for any operational conditions. The BPCM shall have protection to ensure that the balancing does not turn on when it is not intended to balance.
The BPCM shall also diagnose the following for each of the balancing circuit and take appropriate actions:
¡¤ Cell Balance Circuit Stuck Open
¡¤ Cell Balance Circuit Stuck Closed
¡¤ Cell Balance Circuit Normal

#### Cell Balance Mode (Functional)
Cell Balance Mode
The BPCM shall communicate the balancing state on the internal battery CAN bus with the signal HVBatBalMd.
¡¤
¡¤

### Thermal Management System Controls (Functional)
Thermal Management System Controls
The BPCM shall control the Battery Coolant Pump (BCP) and Battery Coolant Heater (BCH) to maintain the High Voltage Battery Pack temperature at normal ranges. HCP is the controller for BCP and BCH. This is accomplished by the BPCM acting as CAN to LIN gateway for information from the BCP and BCH to HCP and vice versa.
Teams shall implement two timing calibrations related to the BCP in the following scenarios:
· The BPCM shall start LIN communication with the BCP within a calibrate-able time after power up.
· When the BPCM starts LIN communication, the BCP shall start responding via LIN communication within a calibrate-able time.
If communication is lost between the BPCM and the BCP, then the BPCM shall report all related CAN Low Temperature Active Pump signals as “SNA”. If the BCP reports that it has a communication error, then the BPCM shall report all related CAN Low Temperature Active Pump signals as “SNA”.
| HCP → BPCM (CAN) | BPCM → BCP (LIN) | BPCM → HCP (CAN) | BCP → BPCM (LIN) |
| --- | --- | --- | --- |
| Thermal_Command (0x3EE) | BCP_REQ | BPCM_LTRActPump1 (0x3EA) | BCP_STAT |
| LTAP_Cmd | BCP_RPM_REQ | LTAP_Crnt | BCP_RPM_TGT |
| LTAP_Failsafe_ACT | BCP_POST_RUN_REQ | LTAP-PmpRPMTgt | BCP_RPM_ACTL |
| LTAP_PostRunCom | BCP_FL_SAFE_ACTVT | LTAP_RPMAct | BCP_VLTG |
|  |  | LTAP_Temp | BCP_TEMP |
|  |  | LTAP_Vlt | BCP_CURR |
|  |  | BPCM_LTRActPump2 (0x3EB) | BCP_FL_SAFE_ACTVTD |
|  |  | LTAP_AirPreErr | BCP_LMP_HM_AN_ON |
|  |  | LTAP_Deblock | BCP_AIR_PRE_ERR |
|  |  | LTAP_DryRun | BCP_OVR_TMP_ERR |
|  |  | LTAP_Failsafe | BCP_OVR_CUR_ERR |
|  |  | LTAP_LimpHmAnON | BCP_DR_RN_ERR |
|  |  | LTAP_MontrngRPM | BCP_VLTG_ERR |
|  |  | LTAP_NodeErr | BCP_DBLK_ACTV |
|  |  | LTAP_OvrCrnt | BCP_MONTRNG_RPM |
|  |  | LTAP_OvrTemp | BCP_NODE_ERR |
|  |  | LTAP_PostRunSts | BCP_POST_RUN_STAT |
|  |  | LTAP_RespErr | RsErr_BCP_PUMP |
|  |  | LTAP_Supplier | BCP_VER |
|  |  | LTAP_SuppVltErr | BCP_VER |
|  |  |  | BCP_SUPPLIER |

#### Heater Command (Functional)
Heater Command
Teams shall implement two timing calibrations related to the BCH in the following scenarios:
¡¤ The BPCM shall start LIN communication with the BCH within a calibrate-able time after power up.
¡¤ When the BPCM starts LIN communication, the BCH shall start responding via LIN communication within a calibrate-able time.
When BPCM controller communication network is established, the BPCM shall communicate all the following related variables to the respective controllers:
| HCP ¡ú BPCM (CAN) | BPCM ¡ú BCH (LIN) | BPCM ¡ú HCP (CAN) | BCH ¡ú BPCM (LIN) |
| --- | --- | --- | --- |
| Thermal_Command (0x3EE) | CCMLIN18Fr02 | BPCM_BattHtr1 (0x3EC) | HVCHLIN18Fr02 |
| BATHTR_Enbl | HvWtrHeatrPwrCnsAllwd | BATHTR_HVCurrCns | RsErr_BCH |
| BATHTR_PwrCnsAllwd | HvWtrHeatrWtrTDes | BATHTR_MeasuredHV | HvCooltHeatrWarnFltInCom |
| BATHTR_WtrTempDes | HvCooltHeatrEnad | BATHTR_PwrCnsAct | HvCooltHeatrWarnHvOutOfRng |
|  |  | BATHTR_PwrCnsDes | HvCooltHeatrWarnULoOutOfRng |
|  |  | BPCM_BattHtr2 (0x3ED) | HvCooltHeatrWarnCooltTOutOfRng |
|  |  | BATHTR_CoolantInletSnsrFlt | HvCooltHeatrProtnOfSelfTmpHwProtn |
|  |  | BATHTR_CoolantOutletSnsrFlt | HvCooltHeatrProtnOfSelfTmpOvrheatg |
|  |  | BATHTR_CoolantTempInlet | HvCooltHeatrSnsrFltCooltTInSnsrFlt |
|  |  | BATHTR_CoolantTempOutlet | HVCHLIN18Fr02 |
|  |  | BATHTR_HCSensorFlt | HvCooltHeatrSnsrFltCooltTOutSnsrFlt |
|  |  | BATHTR_RespErr | HvCooltHeatrSnsrFltTInMtrlSnsrFlt |
|  |  | BATHTR_SelfProtectHW | HvCooltHeatrSrvRqrdCircForDrvrShoOrOpen |
|  |  | BATHTR_SelfProtectOvrHeat | HvCooltHeatrSrvRqrdICnsOutOfRng |
|  |  | BATHTR_ServiceCurrOutofRng | HvCooltHeatrSrvRqrdMemErr |
|  |  | BATHTR_ServiceDrvrCirc | HvCooltHeatrSrvRqrdSrvRqrd |
|  |  | BATHTR_ServiceMemErr | HVCHLIN18Fr01 |
|  |  | BATHTR_ServiceRqrd | HvCooltHeatrSts |
|  |  | BATHTR_Status | HvCooltWtrHeatrWtrTInIntk |
|  |  | BATHTR_WarnCommFlt | HvWtrHeatrWtrT |
|  |  | BATHTR_WARNCoolantTempOOR | HvCooltHeatrICns |
|  |  | BATHTR_WarnHV_OOR | HvCooltHVmeas |
|  |  | BATHTR_WarnLV_OOR | HvHeatrPwrCns |
|  |  |  | HvHeatrPwrCnsDes |

#### Thermal Runaway Requirements (Functional)
Thermal Runaway Requirements
Industry requirements (not validated by competition):
· As per the GB/T regulation, the driver should be notified/alerted to evacuate the vehicle 5mins prior to a hazardous situation which is caused by thermal propagation.
· The BPCM should detect a thermal runaway at least 30 mins prior to a hazardous situation and vehicle shutdown.
For the competition, teams should conduct a simple threshold check using the pack pressure sensor to detect thermal runaway. The default value for this threshold is 0.4 psi.
The BPCM shall send ThermalRunaway_Warning (in message HybridRMS_Safety) = ‘No_Thermal_Runaway’ when BPCM detects the battery is in normal operating mode with no thermal hazardous detected.
In the case that thermal propagation is detected, the BPCM shall send ThermalRunaway_Warning = ‘Thermal_Runaway_Detected’ to the Hybrid Controller.
When thermal runaway is detected, the BPCM shall latch Thermal_System_Relay_Status and lock the contactor to ‘OPEN’ for next key cycle, until the Battery is replaced or an override is performed by a service tool.

### State of Charge (SOC) Requirements (Functional)

#### SOC Algorithm (Functional)
SOC Algorithm
The BPCM shall determine Battery State of Charge (SOC) based on inputs of battery cell temperatures, battery pack current, and cell voltages. This shall be done by a Team-defined algorithm, which shall be used to achieve the desired accuracy and robustness.
The SOC algorithm shall internally estimate the SOC of every cell/cell block in the battery pack. Cell block is a group of parallel cells. Internal BPCM CAN signals shall be available to report the SOC of every cell/cell block. The recommended naming convention of these signals is HVBat_SOCcellXXX, with the incrementing cell number 001, 002, 003, and continue per the required number of cells. The inputs into the SOC algorithm that are stored in memory shall be accessible by a DID.
The inputs into the SOC algorithm that are stored in memory shall be accessible by a DID. Each cell/cell block capacity and cell resistance value shall be a DID. Any additional inputs shall be identified and updated in the Diagnostic Definition Table (DDT) as necessary.

#### Changing SOC Value (Functional)
Changing SOC Value
Teams are required to provide a means of changing the SOC for the development of over and under voltage control and observation of SOC corrections. The SOC change shall happen immediately and does not require a key cycle.

#### SOC Definitions (Functional)
SOC Definitions
State-of-Charge (SOC) is defined as the remaining percentage pack level SOC as defined by the blending equation. SOC shall be expressed as 100% denoting full charge and 0% defining a depleted battery.
The definition of SOC=100% and SOC=0% shall be based on a SOC-OCV relationship as determined from cell characterization. Cell Characterization in this specification typically refers to the method of cell pulse testing (e.g. HPPC) to determine equivalent models parameters (ohmic/dynamic resistance, time constraints).
It is expected that the SOC-OCV relationship look-up-table shall be able to accurately map cell voltage to SOC when the battery is in a sufficiently rested state, i.e. zero current for sufficient time and at thermal equilibrium. Teams may find an example SOC-OCV curve on Box.
HVBatSOC is a pack level SOC signal that blends the minimum and maximum estimate SOC cells/cell blocks into a single percentage signal. The following blending equation shall be used:
MidPoint = (MaxCellSOC + MinCellSOC) / 2;
UpperMid = SOCMaxLimit - ((MaxCellSOC - MinCellSOC)/2);
LowerMid = SOCMinLimit + ((MaxCellSOC - MinCellSOC)/2);
// base the weight factor for max and min cell soc on location of midpoint
// within the possible midpoint range
LowWeightNum = (UpperMid - MidPoint);
LowWeightDen = max((UpperMid - LowerMid),1e-6 );
// update the weight used to determine how important the min cell soc will be
LowWeight = LowWeightNum / LowWeightDen;
If LowWeight<0 then LowWeight=0;
If LowWeight>1 then LowWeight=1;
// update the weight used to determine how important the max cell soc will be
HighWeight = 1 - LowWeight;
BlendedValue = HighWeight*MaxCellSOC + LowWeight*MinCellSOC
The calibrations SOCMaxLimit and SOCMinLimit indicate extreme values such that when the maximum cell SOC >= SOCMaxLimit then HVBatSOC=MaxCellSOX. When the minimum cell/cell block SOC <= SOCMinLimit then HVBatSOC=MinCellSOC.
An example depiction of HVBatSOC blending is shown below for a typical application.
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
#### CAN Signals Associated with SOC (Functional)
CAN Signals Associated with SOC
| CAN Signal | Tx/Rx | Description |
| --- | --- | --- |
| HVBatSOC | Tx | This is the battery SOC described in Q-3 |
| HVBatSOCV | Tx | This indicates the validity of the HVBatSOC signal |
| HVBatSOCMax | Tx | This signal represents the SOC of the cell/cell block with the highest SOC |
| HVBatSOCMin | Tx | This signal represents the SOC of the cell/cell block with the lowest SOC |
| HVBatFull_Amp_Hr_Capacity | Tx | This signal represents the amp hour capacity of the battery pack (as tested by the prescribed capacity test mentioned above). |

### State of Power (SOP) Requirements (Functional)
State of Power (SOP) Requirements
The State of Power (SOP) algorithm in the BPCM software will need to report power limits based on parameters, including the SOC, temperature and battery aging factors. These power limits affect vehicle drivability and determine the vehicle usage of the battery under all conditions and states. The HCP is responsible for abiding by these power limits.
Note that BPCM shall enable the power limit flag and step change power limits to +/- 3kW in any of the following cases:
¡¤ During Loss of Communication (LOC) with the Vehicle controller
¡¤ BUS Off
¡¤ Invalid CAN data active fault.

#### Power Limit Estimation Algorithm (Functional)
Power Limit Estimation Algorithm
Battery power limits with three timing durations shall be required: instantaneous, short term, and long term. Unless otherwise stated, the instantaneous power limit, short-term power limit, and long-term power limit refers to the 2 sec power limit, 10 sec power limit, and 30 sec power limit, respectively. This is the case for both charge and discharge.
The charge power limits shall be based upon the maximum cell voltage in the battery pack, while the discharge power limits shall be based upon the minimum cell voltage in the battery pack.
The power limits shall be based on the minimum battery pack temperature for low temperature and the maximum battery pack temperature for high temperature.
The BPCM software shall not impose additional power deratings for ensuring that the power limits are not exceeded. This is the responsibility of the HCP. Power limits and charging current limits broadcast by the BPCM shall be affected by changing the SOC.

#### Static Power Limiting Tables (Functional)
Static Power Limiting Tables
Static power limit input tables are provided on Box. The tables include entries for the SOC at full vehicle charge and entries for the temperatures and SOCs when the power limits become zero. The information must be provided in proper formats as defined and requested by Competition Organizers.
Maximum currents shall be respected in the power-limiting algorithm to prevent over-current scenarios. The normal operational range for SOC shall include SOC accuracy such that there are no power limits less than 9 kW under normal conditions.
Separate maximum charge/discharge current tables shall also be provided for short term and continuous duration. These tables shall include entries for SOC and temperatures. These maximum currents shall be respected in the power-limiting algorithm to prevent over-current scenarios.

#### Power Limits for Charge and Discharge (Functional)
Power Limits for Charge and Discharge
Initial software for test vehicles shall have mutually agreed upon conservative values.
The BPCM shall broadcast over CAN for the 2, 10, 30, and 180-second discharge and regenerative braking charge power limits. These values always have a positive sign and are in the units of kW.
If the inputs going into determining the power limits become unreliable (due to things like bad sensors, corrupt readings, etc.), the power limit validity should be set to INVALID.
On initialization, the validity bits for the power limits shall indicate VALID (validity bit = 0) within 100 ms of communication. Once accurate power limits are communicated, the power limits validity bits shall stay VALID (validity bit = 0).
The 2-second and 180-second charge and discharge power shall not fall below 9 kW within the operational range of the battery pack. The 10 and 30 second power limits may go to zero power under severe temperature conditions.
The BPCM shall not change the power limits faster than a calibratable value (default = 10kW per second, no step functions from 100kW to 60kW in less than 4 seconds), unless a cell voltage limit is being violated or BEV_HVBatPwrLim_On_BPCM= 1 (Limp Mode). The 10kW per second ¡°De-rating¡± power limit factor is governed by the 180-second De-rating Continuous Power Limit for charge and discharge.
In limp conditions, the power limits shall step change to calibratable value (Ke_v_LimpRegenPwr and Ke_v_LimpDischargePwr).
Exceeding the power limits in normal operation shall be acceptable for a duration of one second with an increase of 20% of the communicated power limit (e.g., if the communicated power limit is 30kW, the power used could be 36kW for one second in a 10 second timeframe). The decision to exceed power limits is determined by the HCP (vehicle controller).
In limp conditions, the allowable power excursions shall be an additional to 6kW for less than 1 second. This is to allow for high voltage devices such as compressors and heaters to change power modes.
Additional power limiting shall be allowed to occur due to loss of sensor inputs.
The values and conditions of the additional power limiting shall be described in the Component Protection Strategy (described elsewhere in this document).
When the power limits are reduced due to loss of sensor inputs, a CAN signal, BEV_HVBatPwrLim_On_BPCM, shall indicate to the HCP (vehicle controller) that additional power limiting is occurring.
When in charge mode, the charge power limits (for regen) shall be based on the max cell voltage threshold used during plug-in charge.

#### Continuous Power Limit (Functional)
Continuous Power Limit
The Continuous Power Limit is a software algorithm that protects the battery from quasi-continuous (prolonged) charge discharge events (e.g. downhill regen and highway/uphill discharge). The Continuous Power Limit strategy has been successfully used in other Stellantis EV programs to protect from a potential voltage collapse prospective.
Continuous Power Limits are in addition to 2/10/30-second power limits. The 2/10/30-second power limits shall de-rate to the continuous power limit based on a 180-second rolling window concept. The de-rating shall be subject to a separate slow slew rate of 1 kW/s. The final outputted power will still be subject to a 10 kW/s slew rate.
Voltage collapse can occur in continuous depletion at all temperatures. The worst condition is near 10 degrees C. Continuous Power Limits should prohibit voltage collapse in all conditions.
An internal CAN signal shall report the continuous power.
Example of Slew Rate:
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Example of Rolling Window:
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Example of Algorithm:
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
#### Accuracy of Power Limit Estimation (Functional)
Accuracy of Power Limit Estimation
The accuracy of the power limit signals and calculations shall be at least 90% of the actual battery power capability, unless otherwise stated.
This accuracy requirement shall be met in a conservative manner, such that operating limits shall always be respected. For example, an error that would result in over/under voltage is unacceptable even if it is within the +/- 5% target accuracy.
This accuracy requirement shall include variables such as temperature, battery age, duty profile (power v. time, aggressive v. non-aggressive), sensor measurement errors, and cell imbalances.
A separate SOP validation document shall be provided to Stellantis to describe MIL, HIL, pack, and vehicle testing procedures used to validate the SOP algorithms. The methodology shall include Stellantis provided drive cycles with periodically inserted power pulses of magnitude determined online by the SOP algorithm.
Error metrics to assess accuracy based on the limiting conditions (voltage-limited, current-limited, power-table limited, battery safety limited, etc.) shall be described in detail in the separate SOP validation document. Percentage error in the case of voltage-limited conditions is calculated based on how close the tested power pulses reached the limit. For table-based limits (current/power), percentage error is calculated by using the reported power.

#### CAN Signals Associated with Power Limiting (Functional)
CAN Signals Associated with Power Limiting
| CAN Signal | Tx/Rx | Description |
| --- | --- | --- |
| BPCM_HVBatChrgPowInstant | Tx | High voltage battery charge power (instant window) |
| BPCM_HVBatChrgPowLong | Tx | High voltage battery charge power (long window) |
| BPCM_HVBatChrgPowShort | Tx | High voltage battery charge power (short window) |
| BPCM_HVBatDischrgPowInstant | Tx | High voltage battery discharge power (instant window) |
| BPCM_HVBatDischrgPowLong | Tx | High voltage battery discharge power (long window) |
| BPCM_HVBatDischrgPowShort | Tx | High voltage battery discharge power (short window) |
| TotalAmpHrCapacity | Tx | Indicates additional power limiting is occurring due to Component. |
| BEV_HVBatPwrLim_On_BPCM | Tx | Limp Home mode enabled |

### (Optional) State of Health (SOH) Requirements (Functional)
(Optional) State of Health (SOH) Requirements
For this competition, the following State of Heath requirements are optional, and will not be tested. The following requirements should be used to set hardcoded values (without an algorithmic implementation) in the BMS to allow the vehicle to operate.
SOH capacity and resistance estimation shall be performed on each cell internally through algorithms. The signals HVBatSOH and HVBatSOHLow will report worst case conditions among all cells.

#### SOH – Capacity (Functional)
SOH ¨C Capacity
The BPCM shall send a CAN signal that communicates the relative capacity of the battery pack SOH, TotalAmpHrCapacity. This value shall change with age and is defined at room temperature and 100% SOC. It is the value one would get if the Capacity Test Procedure was executed on the battery pack (this procedure specifies the temperature and discharge rate).
The reported value of TotalAmpHrCapacity shall have an error from actual capacity by no more than 5%. If the value of TotalAmpHrCapacity becomes unreliable, there shall be a validity signal which signifies this.
The service end-of-life for capacity shall be defined as when the TotalAmpHrCapacity has reached a level below 70% of the initial value on a new battery pack. The BPCM shall request the MIL light to illuminate when the TotalAmpHrCapacity has fallen below a calibratable value (default: 70% of the initial value for a new pack). This will be further defined in the DTC Matrix.
The value of TotalAmpHrCapacity shall be stored in a DID.
The reported value of TotalAmpHrCapacity shall be equal to the applied capacity, while the estimation algorithm is running. The value of TotalAmpHrCapacity shall be updated at power up.
The BPCM shall store the value of TotalAmpHrCapacity in EEPROM, minimally upon shutdown, and use the value on the next wake-up.
The maximum change in TotalAmpHrCapacity shall be no more than 4% for a single update. A provision for a service routine which can set the value of TotalAmpHrCapacity to any desired value shall be provided.
The SOH capacity estimation algorithm shall include an empirical model to be used in cases when online capacity estimates are unavailable or known to be poor. For example; during situations involving mainly long-term charge sustaining operation the on-line SOH capacity estimation may not be accurate enough. To protect against such scenarios an empirical capacity fade model needs to be implemented. This empirical model shall take inputs of measured temperature, sleep/drive times, and battery charge/discharge usage to update capacity and its fading.
The reported SOH capacity estimation shall be a blended value between online estimated capacity and empirical model estimated capacity.
A separate SOH validation document will be provided to Stellantis to describe MIL, HIL, pack, and vehicle testing procedures used to validation capacity estimation accuracy. In particular, multi-day and/or multi-key on/off cycles shall be used to demonstrate robustness of the capacity estimation algorithm in the presence of sensor errors, battery aging effects, cell imbalances, and initialization errors.

#### SOH – Resistance (2 Signals) (Functional)
SOH ¨C Resistance (2 Signals)
The signal HVBatSOHLow will be used as an indicator value to assess the resistance of the battery as a percentage of health. The maximum cell charge and discharge resistance of the battery will be estimated as internal values. There will be an internal HVBatSOHrC and HVBatSOHrd signal that will compute SOHr charge and discharge respectively to derive HVBatSOHLow.
A value of HVBatSOHrC=100% indicates the maximum cell charge resistance at Beginning of Life (BOL). The corresponding resistance value is obtained from BOL cell characterization.
End-of-Life charge resistance shall be determined from the cell characterization of aged end of life cells. For example; cells that have been aged for four-seasons aging and/or cells that have been aged to an end-of-life capacity value. HVBatSOHrC=70% shall be mapped to the Charge Resistance value of EOL charge resistance as defined above. Values between 50% and 70% will indicate excessive resistance growth.
HVBatSOHrD indicates the Discharge Resistance Health. A value of HVBatSOHrD=100% shall indicate the discharge resistance value is at the BOL, using the same BOL cell characterization as described above.
HVBatSOHrD=70% shall indicate that the discharge resistance is at the EOL value. The corresponding value of the EOL discharge resistance shall be determined using the same cell characterization of EOL cells as described above.
The final reported value HVBatSOHLow shall report the minimum of HVBatSOHrC and HVBatSOHrD. The fundamental concept is that HVBatSOHLow shall provide the resistance based health assessment of the cell.
HVBatSOH shall be calculated and filtered at a calibratable high SOC window (70 to 100% SOC) and scaled to a calibratable point (default: 85% SOC). Teams may use the following equation to calculate this instead of the the default 85%:
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where kCAP, kRd, koffset are calibratable parameters to define HVBatSOH.
The end of life resistance shall be defined as when either of the resistance based SOH signals leads to a greater than 30% degradation in the BOL (beginning of life) power as calculated in the BPCM static power limits at 25 deg C.
The BPCM shall request the MIL light to illuminate when either of these resistances based SOH signals falls below a calibrated value (default: that value of resistance which causes the power as calculated in the BPCM static power limits at 25 deg C to fall below 30% of the BOL value). For example, values of HVBatSOH and HVBatSOHLow in the range of 50-70% are anticipated to result in power fades of 30% or more with respect to BOL power.
Both resistance based SOH CAN signal values shall be stored in a DID (to be defined in the program DDT).
A separate SOH validation document will be provided to Stellantis to describe MIL, HIL, pack, and vehicle testing procedures used to validation SOH impedance estimation accuracy. In particular, multi-day and/or multi-key on/off cycles shall be used to demonstrate robustness of the algorithm in the presence of sensor errors, battery aging effects, cell imbalances, and initialization errors.

#### Amp-Hour Throughput (Functional)
Amp-Hour Throughput
The cumulative amp-hour throughput for the battery shall be calculated for both negative values of current (charge) and positive values of current (discharge).
Both charge and discharge amp-hour throughput cumulative values shall be stored in a DID (to be defined in the program DDT).

#### Battery Data Recorder / Battery: Battery Data Recorder / Battery Usage History (BUH) (Functional)
Battery Data Recorder / Battery Usage History (BUH)
Any values being recorded by the BPCM to track the usage of the battery pack (battery data recorder) shall be fully explained by the Team.
All battery data recorder values shall be stored in a DID (to be defined in the program DDT).

#### CAN Signals Associated with SOH (Functional)
CAN Signals Associated with SOH
| CAN Signal | Rx/Tx | Description |
| --- | --- | --- |
| TotalAmpHrCapacity | Tx | Full capacity of the battery (per Capacity Test Procedure). High voltage battery pack total amp-hour capacity |
| HVBatSOH | Tx | Resistance based SOH value measured at high SOC. |
| HVBatSOHLow | Tx | Resistance based SOH value measure at low SOC. |

### Diagnostics Requirements (Functional)
Diagnostics Requirements
Teams shall refer to the DTC Matrix (VF_UDS_DTC_Criteria Matrix_BWC) sent over FileBox for information on DTC implementation. Teams should additionally perform a DFMEA and include any additional diagnostics identified by the DFMEA.
Unless otherwise specified, faults shall not be latched between key off/on cycles. Exceptions to not latching faults between key off/on cycles shall be approved by Competition Organizers and currently only include, impact response, isolation (within battery pack only), and welded contactors. No DTCs shall be present after a flash event except for those that were present before the flash event.
Any device that communicates faults to the BPCM through fault flags shall have a separate DTC and DIDs for counting events. Any fault that opens contactors or prevents contactors from closing shall have a unique DTC assigned to it.
All DTCs shall have two records: the first and latest instance that the DTCs were present. Teams should also record additional environmental data for DTCs that are difficult to determine the root cause of when in the field.
The setting of a DTC on a fail event shall not cause the setting of other DTCs. For example, the setting of the fuse circuit fault should not result in the setting of a blown fuse fault.

#### Diagnostic Robustness (Functional)
Diagnostic Robustness
It is required that all diagnostics be robust to reduce the probability of false failures and ensure that real failures are detected. The robustness will be analyzed and achieved by the following tasks.
For all diagnostic circuits, a tolerance stack-up analysis for all the components in the circuit shall be conducted. This is to ensure that the DTC will be calibrated in a manner which includes all the variable inputs to the elements of the circuit over the life of the vehicle (e.g., temperature, age, voltage references, etc.).
All inputs used to determine the diagnostic shall be available in the internal CAN bus so that they can be monitored during vehicle development.
The internal CAN bus shall remain awake during shutdown for as long as possible so that the diagnostics occurring during shutdown can be analyzed. The ePT CAN line will remain silent during shutdown.
The maturation times shall be calibrated to be as long as possible. Once matured, the reaction for those DTCs which influence drivability (e.g., contactors opening, power limiting to zero kW) shall be delayed by a minimum calibratable value (variable Ke_t_DTCdelay, default: 30 seconds).
The priority for the work flow is shown below.
¡¤ Those diagnostics which open contactors during vehicle driving
¡¤ Those diagnostics which prevent contactors from closing at power up
¡¤ Those diagnostics which light the MIL light
¡¤ Those diagnostics which inhibit plug-in charge
¡¤ All other diagnostics
Teams should note that they should organize their list of implemented DTCs by the above categories and additionally track information regarding the implementation, testing and validation of their DTCs.
The BPCM should monitor and diagnose its critical systems. When a fault is detected, appropriate reactions should be taken to ensure safety and to minimize damage to the hardware whenever possible. It is also important to not have false failures that interfere with the ability to make use of the battery. So, Teams must implement the enable conditions, mature threshold requirements and mature time requirements as specified in the DTC Matrix.
Teams will need to send out all diagnostic status that BMS would send out. Teams can implement their own diagnostics on their Team¡¯s private CAN.

#### BPCM Warning and [Shutdown SW] C: BPCM Warning and [Shutdown SW] Contactor Open Requirements (Functional)
BPCM Warning and [Shutdown SW] Contactor Open Requirements
The BPCM shall protect itself from improper usage of the vehicle by using warning stages to the vehicle, as to reduce the probability of damage to the battery and/or cause a failed start condition or a vehicle to be disabled during operation.
The warning stages shall be communicated over CAN as follows:
¡¤ HVBatCntctrOpn ¨C A notification that contactors will open in no more than a calibrated amount of time (default: 1500 ms). This gives the vehicle controller time to react and lower current before contactors open.
¡¤ HVBatCntctrReq ¨C A request to return to normal operating range or request to open contactors. This will transition to HVBatCntctrOpn if the conditions persist for a calibratable amount of time (default = 30 s).
The Team shall provide to Competition Organizers a plan for minimizing shutdowns and vehicle performance issues which lists all reasons why contactor open, contactor won¡¯t close, if power limits are reduced, and how DTC¡¯s will be set through cascading failures. The plan shall include what happens when sensor values are lost or invalid, including any mitigating actions taken.
Sensor values shall be substituted with other available data to the maximum extent possible. Substitution of values read by sensors shall be conducted in a manner most appropriate for accuracy and continued vehicle functionality.

#### Service Routine for Battery Pack: Service Routine for Battery Pack Outside Normal Voltage Range (Functional)
Service Routine for Battery Pack Outside Normal Voltage Range
There shall be a service routine available for the purpose of restoring battery packs back to the normal voltage range. This would be for battery packs that for some reason have gotten voltages too high or too low but are still at a point where they are salvageable. The routine will require the contactors to close to allow the vehicle to either charge the battery pack (using the motor) or discharge the battery pack.

#### Validation of DTCs (Functional)
Validation of DTCs
The Team shall develop a method to test all DTCs with a breakout box for the signal lines leaving the battery pack.
A pack can be instrumented with the ability to cause all faults manually or through software in the vehicle. If it is done using software other than CANalyzer, then a computer with that software and all supported hardware and harnesses should be provided.
The purpose of DTC testing at the vehicle level is to verify the integration functionality (fault reactions and vehicle response). Testing fault maturation, enablement, FOMs, status byte, etc. shall be conducted at the pack level by the Team.
DTC tests at the vehicle level will fall into a few categories:
¡¤ Bridge layer ¨C Some tests will require bridge layer to induce false failures. Teams shall provide any out of the ordinary harness for connection, software, and instructions to perform these tests.
¡¤ Breakout box ¨C Some tests will require a breakout box to simplify the ability to manipulate the wiring harness to the BPCM. (As some wiring to the BPCM may be internal to the battery for this program this will need to be considered for the instrumented pack section).
For any DTC that has multiple failure conditions, a DID shall be defined with a root cause and the failure associated with it. And the path which set the DTC shall be identified in the environmental data.
All DTCs shall be thoroughly validated by the Team. A test suite for testing shall be released soon that will go into details as to what tests may be conducted. At competition events, the DTC tests suite shall also be tested by Competition Organizers.

#### Diagnostic Retry Strategy (Functional)
Diagnostic Retry Strategy
A Diagnostic Retry Strategy is required to reduce false failures and ensure conditions are true, that result in a “No Start” condition, warning conditions to the customer, or a contactor lock out on the following key cycle. A diagnostic retry attempt strategy will authenticate or disprove failures using singular or multiple test.
Some retry attempts may cause issues for power moding, which will need to be reviewed and approved by the OSC.
Team shall provide a list of “all” the DTCs that cause the following: a “No Start” condition, warning conditions to the customer, or a contactor lock out where contactors will not close on the following key cycle.
Based on the DTC Matrix, DTCs will be selected to go through a process of availability engineering that will focus on increasing testability. DTCs will be reviewed to determine what test and retry attempts can take place through a power down or power up event.
For Diagnostic Retry Strategy implementation, the priority of implementation is.
1. No Start – DTC’s that cause a contactor lockout
2. DTC’s that cause warning indications
Students should also be aware that on-demand monitor type DTC’s cause a contactor lock out, where contactors will not close on the following key cycle.

### Appendix A (Functional)

#### Sensors (Functional)
Sensors
Problem Illumination Lights
MIL_OnRq_BPCM ¨C BPCM request MIL light to illuminate due to an OBDII fault
HEV_OnRq_BPCM ¨C BPCM requesting service light to illuminate due to a DTC

#### CAN Signals (Functional)
CAN Signals
A signal list will be provided by Stellantis in a CAN DBC file, showing signals that shall be sent from or received by the BPCM. These signals are subject to change given the vehicle program DBC File.
For all CAN signals for which there are associated validity bits, the strategy for what makes these signals INVALID shall be documented and submitted to Competition Organizers for approval.
The value of the validity bit shall be 1 when INVALID and 0 when VALID.
All validity bits that the BPCM transmits shall not be set to INVALID until the corresponding DTC has fully matured. This is to avoid the vehicle controller setting an ¡°Invalid Data Received from Battery Pack Control Module¡± DTC based on a transient event.

### Abbreviations (Functional)
Abbreviations
ADDRESS: Automated Document Retrieval & Engineering Standards System
BCH: Battery Coolant Heater
BCP: Battery Coolant Pump
bev: battery electric vehicle
BMS: Battery Management System
BPCM: Battery Pack Control Module
CAN: Controller Area Network
CAN FD: Controller Area Network Flexible Data
CC: Continuous Conformance
CDA: FCA Diagnostic Application
CPTS: Component Parts Traceability System
CRC: Cyclic Redundancy Check
CSC: Cell Supervising Circuit
CVR: Component Verification Report
DDT: Diagnostic Definition Table
DFMEA: Design Failure Modes and Effects Analysis
DID: Data Identifier
DPRS: Diagnostic Performance Requirements Specification
DTC: Diagnostic Trouble Code
DV: Design Verification
DVP&R: Design Verification Plan & Report
E2E: End to End (Communication Protection)
ECU: Electronic Control Unit
ED&D: Engineering Design & Development
EEPROM: Electrically Erasable Program Read Only Memory
EMC: Electromagnetic Compatibility
ePT: Electrified Power Train
EOL: End of Line / End of Life EV: Electric Vehicle
EVCU: ELECTRIC VEHICLE CONTROL Module (contains HCP)
EVSE: Electric Vehicle Supply Equipment
FCA: Fiat Chrysler Automobiles
FMVSS: Federal Motor Vehicle Safety Standard
FOM: Figure of Merit
HCP: Hybrid Charge Controller
HEV: Hybrid Electric Vehicle
HIL: Hardware in the Loop
HV: High Voltage
HVBS: High Voltage Battery System
HVIL: High Voltage Interlock
IOD: Idle Off Draw (current drawn while controller is OFF/asleep)
LED: Light Emitting Diode
LIN: Local Interconnect Network
LOC: Loss of Communication
LOI: Loss of Isolation
LV: Low Voltage
MC: Message Counter
MIL: Model in the Loop / Malfunction Indicator Light
MRD: Material Received Date
NM: Network Management
NMIF: Network Management Interface
NVRAM: Non-volatile Random Access Memory
OBC/OBCM: On Board Charger/On Board Charge Module
OBD: On-Board Diagnostic
ORC: Occupant Restraint Controller
PID: Parameter Identifier
PIM: Power Inverter Module (contains HCP), evcU repalces PIM in bev vehicles
PV: Production Validation
RAM: Random Access Memory
ROM: Read Only Memory
RTC: Real Time Control
SNA: Signal Not Available
SOB: State of Battery
SOC: State of Charge
SOH: State of Health
SOF: Start of Frame
SOP: State of Power
SRD: Software Requirements Document
TTF: Test to Failure
UDS: Unified Diagnostic Services

### - Change Log (Functional)
- Change Log
| Date | Revision | Section | Change Description | Initials |
| --- | --- | --- | --- | --- |
| 1/15/2024 | 0 | ALL | Initial Document Release | OSC |
| 8/01/2024 | 1 | Multiple | Adjusted documentation to reflect breaktor requirements, remove PWM requirements that are not applicable and other highlighted updates | OSC |
| 10/24/2024 | 2 | I-6 | Clarified language on precharge sequence for breaktor | OSC |
| 1/22/2025 | 3 | K | Added impact response requirements | BC |
| 1/22/2025 | 3 | H-1.3 | Removed HVIL repeated requirement | OSC |
| 2/10/2025 | 4 | Multiple | Adjusted CAN dbc signal names to match current database and remove unused signals | OSC |
| 3/4/2025 | 5 | I-2 | Added Qualified Contactor Command internal variable and description | OSC |
| 4/8/2025 | 6 | Multiple | Clarified implementation of calibrations, internal variables and variables related to Precharge; Updated HVIL section with full form of OORH and OORL | OSC |
| 9/3/2025 | 7 | Multiple | Major revisions for clarity and readability. Following requirements were made optional: ¡¤ Cell Balancing ¡¤ State of Health | OSC |
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|  |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 |
| --- | --- |
